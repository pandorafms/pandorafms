--
-- dcstorag.mib
-- MIB generated by MG-SOFT Visual MIB Builder Version 6.0  Build 88
-- Tuesday, November 25, 2008 at 18:11:03
--

-- Copyright (c) 2002 Dell
-- Module Name: dcstorag.mib
-- Abstract:
-- 	Defines the Dell OpenManage Storage Management SNMP interface.
-- Authors:
-- 
-- Revision History:
-- KEMR (10/23/02) 0.1 - Original draft	
-- 
-- IMPORTANT NOTE
-- MG-SOFT MibBuilder will be used as the tool to change this MIB.  Because of the way the MG-SOFT MIB tools work, a copy
-- of the intermediate file with the extension .bui will be kept in SourceSafe along with the ASCII .mib version.  When 
-- any changes are made to the MIB they will have to be made to the .bui file using MibBuilder and then exported to the
-- .mib file.  If you open the .mib version of the MIB in  MibBuilder, the compiler is run in on the fly and ALL comments 
-- will be removed.  This is a "feature" of the tool and is beyond our control.

	StorageManagement-MIB DEFINITIONS ::= BEGIN
 
		IMPORTS
			OBJECT-TYPE			
				FROM RFC-1212			
			TRAP-TYPE			
				FROM RFC-1215			
			enterprises			
				FROM RFC1155-SMI			
			DisplayString			
				FROM RFC1213-MIB;
	
	
--
-- Type definitions
--
	
		DellStatus ::= INTEGER
			{
			other(1),
			unknown(2),
			ok(3),
			nonCritical(4),
			critical(5),
			nonRecoverable(6)
			}

	
--
-- Node definitions
--
	
		-- 1.3.6.1.4.1.674
		dell OBJECT IDENTIFIER ::= { enterprises 674 }

		
		-- 1.3.6.1.4.1.674.10893
		storage OBJECT IDENTIFIER ::= { dell 10893 }

		
		-- 1.3.6.1.4.1.674.10893.1
		software OBJECT IDENTIFIER ::= { storage 1 }

		
-- The Storage Management MIB (Management Information Base) Group 
-- defines the properties that identify information about the Storage 
-- Management software product and the current status of the system it manages.
		-- 1.3.6.1.4.1.674.10893.1.20
		storageManagement OBJECT IDENTIFIER ::= { software 20 }

		
		-- 1.3.6.1.4.1.674.10893.1.20.1
		softwareVersion OBJECT-TYPE
			SYNTAX DisplayString (SIZE (1..32))
			ACCESS read-only
			STATUS mandatory
			DESCRIPTION
				"Version number of the storage management component of the systems management software."
			::= { storageManagement 1 }

		
		-- 1.3.6.1.4.1.674.10893.1.20.2
		globalStatus OBJECT-TYPE
			SYNTAX INTEGER
				{
				critical(1),
				warning(2),
				normal(3),
				unknown(4)
				}
			ACCESS read-only
			STATUS mandatory
			DESCRIPTION
				"Global health information for the subsystem managed by
				the Storage Management software.  This global status is 
				customized for HP OpenView.  Other applications should 
				refer to the agentSystemGlobalStatus entry in the 
				globalData object group.
				
				Possible values:
				1: Critical
				2: Warning
				3: Normal
				4: Unknown"
			::= { storageManagement 2 }

		
		-- 1.3.6.1.4.1.674.10893.1.20.3
		softwareManufacturer OBJECT-TYPE
			SYNTAX DisplayString (SIZE (1..32))
			ACCESS read-only
			STATUS mandatory
			DESCRIPTION
				"Manufacturer information for the Storage Management software."
			::= { storageManagement 3 }

		
		-- 1.3.6.1.4.1.674.10893.1.20.4
		softwareProduct OBJECT-TYPE
			SYNTAX DisplayString (SIZE (1..64))
			ACCESS read-only
			STATUS mandatory
			DESCRIPTION
				"Product information for the Storage Management software."
			::= { storageManagement 4 }

		
		-- 1.3.6.1.4.1.674.10893.1.20.5
		softwareDescription OBJECT-TYPE
			SYNTAX DisplayString (SIZE (1..128))
			ACCESS read-only
			STATUS mandatory
			DESCRIPTION
				"Product Description for the Storage Management software."
			::= { storageManagement 5 }

		
-- The Storage Management Information Management Information Base (MIB) 
-- Group defines the properties that identify the Storage Management software SNMP agent.
		-- 1.3.6.1.4.1.674.10893.1.20.100
		storageManagementInfo OBJECT IDENTIFIER ::= { storageManagement 100 }

		
		-- 1.3.6.1.4.1.674.10893.1.20.100.1
		displayName OBJECT-TYPE
			SYNTAX DisplayString
			ACCESS read-only
			STATUS mandatory
			DESCRIPTION
				"Name of this management software for display purposes."
			::= { storageManagementInfo 1 }

		
		-- 1.3.6.1.4.1.674.10893.1.20.100.2
		description OBJECT-TYPE
			SYNTAX DisplayString
			ACCESS read-only
			STATUS mandatory
			DESCRIPTION
				"A short description of this management software."
			::= { storageManagementInfo 2 }

		
		-- 1.3.6.1.4.1.674.10893.1.20.100.3
		agentVendor OBJECT-TYPE
			SYNTAX DisplayString
			ACCESS read-only
			STATUS mandatory
			DESCRIPTION
				"The name of the management software manufacturer."
			::= { storageManagementInfo 3 }

		
		-- 1.3.6.1.4.1.674.10893.1.20.100.4
		agentVersion OBJECT-TYPE
			SYNTAX DisplayString
			ACCESS read-only
			STATUS obsolete
			DESCRIPTION
				"This entry is obsolete.  Refer to softwareVersion."
			::= { storageManagementInfo 4 }

		
-- The Global Data Management Information Base (MIB) Group defines the 
-- properties that identify status information about system that the 
-- Storage Management software is managing and about the Storage Management SNMP agent.
		-- 1.3.6.1.4.1.674.10893.1.20.110
		globalData OBJECT IDENTIFIER ::= { storageManagement 110 }

		
		-- 1.3.6.1.4.1.674.10893.1.20.110.1
		agentSystemGlobalStatus OBJECT-TYPE
			SYNTAX INTEGER
				{
				normal(1),
				warning(2),
				nonCriticalError(3),
				failure(4),
				unknown(5)
				}
			ACCESS read-only
			STATUS obsolete
			DESCRIPTION
				"This entry is obsolete.  Please use the value: agentGlobalSystemStatus.
				Note: Enumerated values have changed."
			::= { globalData 1 }

		
		-- 1.3.6.1.4.1.674.10893.1.20.110.2
		agentLastGlobalStatus OBJECT-TYPE
			SYNTAX INTEGER
				{
				normal(1),
				warning(2),
				nonCriticalError(3),
				failure(4),
				unknown(5)
				}
			ACCESS read-only
			STATUS obsolete
			DESCRIPTION
				"This entry is obsolete.  Please use the value: agentLastGlobalSystemStatus.
				Note: Enumerated values have changed."
			::= { globalData 2 }

		
		-- 1.3.6.1.4.1.674.10893.1.20.110.3
		agentTimeStamp OBJECT-TYPE
			SYNTAX INTEGER
			ACCESS read-only
			STATUS mandatory
			DESCRIPTION
				"The last time that the agent values have been updated.
				Universal time in sec since UTC 1/1/70."
			::= { globalData 3 }

		
		-- 1.3.6.1.4.1.674.10893.1.20.110.4
		agentGetTimeout OBJECT-TYPE
			SYNTAX INTEGER (1..10000)
			ACCESS read-only
			STATUS mandatory
			DESCRIPTION
				"Suggested timeout value in milliseconds for how long 
				the SNMP getter should wait while attempting to poll 
				the SNMP agent."
			::= { globalData 4 }

		
		-- 1.3.6.1.4.1.674.10893.1.20.110.5
		agentModifiers OBJECT-TYPE
			SYNTAX INTEGER (1..10000)
			ACCESS read-only
			STATUS mandatory
			DESCRIPTION
				"Agent functional modifiers, when set the modifier is active.
				Bit definitions:
				 Bit 3: agent in debug mode.
				 All other bits are product specific
				"
			::= { globalData 5 }

		
		-- 1.3.6.1.4.1.674.10893.1.20.110.6
		agentRefreshRate OBJECT-TYPE
			SYNTAX INTEGER (1..10000)
			ACCESS read-only
			STATUS mandatory
			DESCRIPTION
				"The rate, given in seconds, at which the cached data for SNMP is refreshed.
				The default value is 300 seconds, or 5 minutes."
			::= { globalData 6 }

		
		-- 1.3.6.1.4.1.674.10893.1.20.110.7
		agentHostname OBJECT-TYPE
			SYNTAX DisplayString
			ACCESS read-only
			STATUS obsolete
			DESCRIPTION
				"This entry is obsolete for Storage Management."
			::= { globalData 7 }

		
		-- 1.3.6.1.4.1.674.10893.1.20.110.8
		agentIPAddress OBJECT-TYPE
			SYNTAX DisplayString
			ACCESS read-only
			STATUS obsolete
			DESCRIPTION
				"This entry is obsolete for Storage Management."
			::= { globalData 8 }

		
		-- 1.3.6.1.4.1.674.10893.1.20.110.9
		agentSoftwareStatus OBJECT-TYPE
			SYNTAX INTEGER
				{
				databaseUp(1),
				databaseDown(2)
				}
			ACCESS read-only
			STATUS obsolete
			DESCRIPTION
				"This entry is obsolete for Storage Management."
			::= { globalData 9 }

		
		-- 1.3.6.1.4.1.674.10893.1.20.110.10
		agentSnmpVersion OBJECT-TYPE
			SYNTAX DisplayString
			ACCESS read-only
			STATUS obsolete
			DESCRIPTION
				"This entry is obsolete.  Refer to softwareVersion."
			::= { globalData 10 }

		
		-- 1.3.6.1.4.1.674.10893.1.20.110.11
		agentMibVersion OBJECT-TYPE
			SYNTAX DisplayString
			ACCESS read-only
			STATUS mandatory
			DESCRIPTION
				"Version of the Storage Management MIB."
			::= { globalData 11 }

		
		-- 1.3.6.1.4.1.674.10893.1.20.110.12
		agentManagementSoftwareURLName OBJECT-TYPE
			SYNTAX DisplayString
			ACCESS read-only
			STATUS mandatory
			DESCRIPTION
				"The Universal Resource Locator (URL) of the systems management software."
			::= { globalData 12 }

		
		-- 1.3.6.1.4.1.674.10893.1.20.110.13
		agentGlobalSystemStatus OBJECT-TYPE
			SYNTAX DellStatus
			ACCESS read-only
			STATUS mandatory
			DESCRIPTION
				"Global health information for the subsystem managed by
				the Storage Management software.  This global status
				should be used by applications other than HP OpenView.
				HP OpenView should refer to the globalStatus in the root level object 
				group.  This is a rollup for the entire agent including 
				any monitored devices. The status is intended to give 
				initiative to a snmp monitor to get further data when 
				this status is abnormal.
				
				Possible values:
				1: Other
				2: Unknown
				3: OK 
				4: Non-critical 
				5: Critical
				6: Non-recoverable"
			::= { globalData 13 }

		
		-- 1.3.6.1.4.1.674.10893.1.20.110.14
		agentLastGlobalSystemStatus OBJECT-TYPE
			SYNTAX DellStatus
			ACCESS read-only
			STATUS mandatory
			DESCRIPTION
				"The previous global status of the system managed by the Storage Management software.
				
				Possible values:
				1: Other
				2: Unknown
				3: OK 
				4: Non-critical 
				5: Critical
				6: Non-recoverable"
			::= { globalData 14 }

		
		-- 1.3.6.1.4.1.674.10893.1.20.110.15
		agentSmartThermalShutdown OBJECT-TYPE
			SYNTAX INTEGER
				{
				enabled(1),
				disabled(2),
				notApplicable(3)
				}
			ACCESS read-only
			STATUS mandatory
			DESCRIPTION
				"Indicates the status of smart thermal shutdown for PV220S and PV221S enclosures.
				Possible values:
				1: Enabled
				2: Disabled"
			::= { globalData 15 }

		
-- The Physical Devices Management Information Base (MIB) group exposes 
-- information about the devices managed by the Storage Management 
-- software and their relationships to each other.
-- This group and all of its associated tables and objects are not
-- supported on Microsoft Windows Advanced Server Limited Edition 
-- 64-bit operating system (Windows.Net-64) on a PE7150.
		-- 1.3.6.1.4.1.674.10893.1.20.130
		physicalDevices OBJECT IDENTIFIER ::= { storageManagement 130 }

		
		-- 1.3.6.1.4.1.674.10893.1.20.130.1
		controllerTable OBJECT-TYPE
			SYNTAX SEQUENCE OF ControllerEntry
			ACCESS not-accessible
			STATUS mandatory
			DESCRIPTION
				"A table of managed RAID controllers. The number of entries
				is related to number of RAID controllers discovered in the
				system.
				Note: The properties in this table may not be applicable to all entries."
			::= { physicalDevices 1 }

		
		-- 1.3.6.1.4.1.674.10893.1.20.130.1.1
		controllerEntry OBJECT-TYPE
			SYNTAX ControllerEntry
			ACCESS not-accessible
			STATUS mandatory
			DESCRIPTION
				"An entry in the table of RAID controllers. A row in this table cannot
				be created or deleted by SNMP operations on columns of the table."
			INDEX { controllerNumber }
			::= { controllerTable 1 }

		
		ControllerEntry ::=
			SEQUENCE { 
				controllerNumber
					INTEGER,
				controllerName
					DisplayString,
				controllerVendor
					DisplayString,
				controllerType
					INTEGER,
				controllerState
					INTEGER,
				controllerSeverity
					INTEGER,
				controllerRebuildRateInPercent
					INTEGER,
				controllerFWVersion
					DisplayString,
				controllerCacheSizeInMB
					INTEGER,
				controllerCacheSizeInBytes
					INTEGER,
				controllerPhysicalDeviceCount
					INTEGER,
				controllerLogicalDeviceCount
					INTEGER,
				controllerPartnerStatus
					DisplayString,
				controllerHostPortCount
					INTEGER,
				controllerMemorySizeInMB
					INTEGER,
				controllerMemorySizeInBytes
					INTEGER,
				controllerDriveChannelCount
					INTEGER,
				controllerFaultTolerant
					INTEGER,
				controllerC0Port0WWN
					DisplayString,
				controllerC0Port0Name
					DisplayString,
				controllerC0Port0ID
					INTEGER,
				controllerC0Target
					INTEGER,
				controllerC0Channel
					INTEGER,
				controllerC0OSController
					DisplayString,
				controllerC0BatteryState
					INTEGER,
				controllerC1Port0WWN
					DisplayString,
				controllerC1Port0Name
					DisplayString,
				controllerC1Port0ID
					INTEGER,
				controllerC1Target
					INTEGER,
				controllerC1Channel
					INTEGER,
				controllerC1OSController
					INTEGER,
				controllerC1BatteryState
					INTEGER,
				controllerNodeWWN
					DisplayString,
				controllerC0Port1WWN
					DisplayString,
				controllerC1Port1WWN
					DisplayString,
				controllerBatteryChargeCount
					INTEGER,
				controllerRollUpStatus
					DellStatus,
				controllerComponentStatus
					DellStatus,
				controllerNexusID
					DisplayString,
				controllerAlarmState
					INTEGER,
				controllerDriverVersion
					DisplayString,
				controllerPCISlot
					DisplayString,
				controllerClusterMode
					INTEGER,
				controllerMinFWVersion
					DisplayString,
				controllerMinDriverVersion
					DisplayString,
				controllerSCSIInitiatorID
					INTEGER,
				controllerChannelCount
					INTEGER,
				controllerReconstructRate
					INTEGER,
				controllerPatrolReadRate
					INTEGER,
				controllerBGIRate
					INTEGER,
				controllerCheckConsistencyRate
					INTEGER,
				controllerPatrolReadMode
					INTEGER,
				controllerPatrolReadState
					INTEGER,
				controllerPatrolReadIterations
					INTEGER
			 }

		-- 1.3.6.1.4.1.674.10893.1.20.130.1.1.1
		controllerNumber OBJECT-TYPE
			SYNTAX INTEGER (1..255)
			ACCESS read-only
			STATUS mandatory
			DESCRIPTION
				"Instance number of this controller entry."
			::= { controllerEntry 1 }

		
		-- 1.3.6.1.4.1.674.10893.1.20.130.1.1.2
		controllerName OBJECT-TYPE
			SYNTAX DisplayString
			ACCESS read-only
			STATUS mandatory
			DESCRIPTION
				"The name of the controller in this subsystem as represented in Storage Management. 
				Includes the controller type and instance.  
				For example: Perc3/QC 1."
			::= { controllerEntry 2 }

		
		-- 1.3.6.1.4.1.674.10893.1.20.130.1.1.3
		controllerVendor OBJECT-TYPE
			SYNTAX DisplayString
			ACCESS read-only
			STATUS mandatory
			DESCRIPTION
				"The controller's (re)seller's name."
			::= { controllerEntry 3 }

		
		-- 1.3.6.1.4.1.674.10893.1.20.130.1.1.4
		controllerType OBJECT-TYPE
			SYNTAX INTEGER
				{
				scsi(1),
				pv660F(2),
				pv662F(3),
				ide(4),
				sata(5),
				sas(6)
				}
			ACCESS read-only
			STATUS mandatory
			DESCRIPTION
				"The type of this controller:
				1: SCSI
				2: PV660F 
				3: PV662F
				4: IDE (Integrated/Intelligent Drive Electronics)
				5: SATA (Serial Advanced Technology Attachment)
				6: SAS (Serial Attached SCSI)"
			::= { controllerEntry 4 }

		
		-- 1.3.6.1.4.1.674.10893.1.20.130.1.1.5
		controllerState OBJECT-TYPE
			SYNTAX INTEGER
				{
				ready(1),
				failed(2),
				online(3),
				offline(4),
				degraded(6)
				}
			ACCESS read-only
			STATUS mandatory
			DESCRIPTION
				"The current condition of the controller's subsystem 
				(which includes any devices connected to it.)
				Possible states:
				0: Unknown
				1: Ready
				2: Failed
				3: Online
				4: Offline
				6: Degraded"
			::= { controllerEntry 5 }

		
		-- 1.3.6.1.4.1.674.10893.1.20.130.1.1.6
		controllerSeverity OBJECT-TYPE
			SYNTAX INTEGER
				{
				warning(1),
				error(2),
				failure(3)
				}
			ACCESS read-only
			STATUS obsolete
			DESCRIPTION
				"This entry is obsolete for Storage Management.
				It was replaced with RollUpStatus and ComponentStatus for each device."
			::= { controllerEntry 6 }

		
		-- 1.3.6.1.4.1.674.10893.1.20.130.1.1.7
		controllerRebuildRateInPercent OBJECT-TYPE
			SYNTAX INTEGER (0..100)
			ACCESS read-only
			STATUS mandatory
			DESCRIPTION
				"The percent of the compute cycles dedicated to rebuilding 
				failed array disks. "
			::= { controllerEntry 7 }

		
		-- 1.3.6.1.4.1.674.10893.1.20.130.1.1.8
		controllerFWVersion OBJECT-TYPE
			SYNTAX DisplayString
			ACCESS read-only
			STATUS mandatory
			DESCRIPTION
				"The controller's current firmware version."
			::= { controllerEntry 8 }

		
		-- 1.3.6.1.4.1.674.10893.1.20.130.1.1.9
		controllerCacheSizeInMB OBJECT-TYPE
			SYNTAX INTEGER
			ACCESS read-only
			STATUS mandatory
			DESCRIPTION
				"The controller's current amount of cache memory in megabytes.  
				If this size is 0, it is less than a megabyte."
			::= { controllerEntry 9 }

		
		-- 1.3.6.1.4.1.674.10893.1.20.130.1.1.10
		controllerCacheSizeInBytes OBJECT-TYPE
			SYNTAX INTEGER
			ACCESS read-only
			STATUS mandatory
			DESCRIPTION
				"The controller's current amount of cache memory that is less than a megabyte.  This combined with the 
				controllerCacheSizeInMB will be the total amount of memory."
			::= { controllerEntry 10 }

		
		-- 1.3.6.1.4.1.674.10893.1.20.130.1.1.11
		controllerPhysicalDeviceCount OBJECT-TYPE
			SYNTAX INTEGER
			ACCESS read-only
			STATUS mandatory
			DESCRIPTION
				"Number of physical devices on the controller channel including both disks and the controller."
			::= { controllerEntry 11 }

		
		-- 1.3.6.1.4.1.674.10893.1.20.130.1.1.12
		controllerLogicalDeviceCount OBJECT-TYPE
			SYNTAX INTEGER
			ACCESS read-only
			STATUS mandatory
			DESCRIPTION
				"Number of virtual disks on the controller."
			::= { controllerEntry 12 }

		
		-- 1.3.6.1.4.1.674.10893.1.20.130.1.1.13
		controllerPartnerStatus OBJECT-TYPE
			SYNTAX DisplayString
			ACCESS read-only
			STATUS obsolete
			DESCRIPTION
				"This entry is obsolete for Storage Management."
			::= { controllerEntry 13 }

		
		-- 1.3.6.1.4.1.674.10893.1.20.130.1.1.14
		controllerHostPortCount OBJECT-TYPE
			SYNTAX INTEGER
			ACCESS read-only
			STATUS obsolete
			DESCRIPTION
				"This entry is obsolete.
				Fibre channel is not supported in Storage Management."
			::= { controllerEntry 14 }

		
		-- 1.3.6.1.4.1.674.10893.1.20.130.1.1.15
		controllerMemorySizeInMB OBJECT-TYPE
			SYNTAX INTEGER
			ACCESS read-only
			STATUS mandatory
			DESCRIPTION
				"Size of memory in megabytes on the controller.  If this size is 0, it is less than a megabyte.  This attribute is only supported on Adaptec controllers.  "
			::= { controllerEntry 15 }

		
		-- 1.3.6.1.4.1.674.10893.1.20.130.1.1.16
		controllerMemorySizeInBytes OBJECT-TYPE
			SYNTAX INTEGER
			ACCESS read-only
			STATUS mandatory
			DESCRIPTION
				"Size of memory on the controller that is less than a megabyte.  This combined with the controllerMemorySizeInMB
				will be the total size of the memory.  This attribute is only supported on Adaptec controllers."
			::= { controllerEntry 16 }

		
		-- 1.3.6.1.4.1.674.10893.1.20.130.1.1.17
		controllerDriveChannelCount OBJECT-TYPE
			SYNTAX INTEGER (1..4)
			ACCESS read-only
			STATUS obsolete
			DESCRIPTION
				"This entry is obsolete.
				Fibre channel is not supported in Storage Management."
			::= { controllerEntry 17 }

		
		-- 1.3.6.1.4.1.674.10893.1.20.130.1.1.18
		controllerFaultTolerant OBJECT-TYPE
			SYNTAX INTEGER { yes(1) }
			ACCESS read-only
			STATUS mandatory
			DESCRIPTION
				"This entry is obsolete.
				Fibre channel is not supported in Storage Management."
			::= { controllerEntry 18 }

		
		-- 1.3.6.1.4.1.674.10893.1.20.130.1.1.19
		controllerC0Port0WWN OBJECT-TYPE
			SYNTAX DisplayString
			ACCESS read-only
			STATUS obsolete
			DESCRIPTION
				"This entry is obsolete.
				Fibre channel is not supported in Storage Management."
			::= { controllerEntry 19 }

		
		-- 1.3.6.1.4.1.674.10893.1.20.130.1.1.20
		controllerC0Port0Name OBJECT-TYPE
			SYNTAX DisplayString
			ACCESS read-only
			STATUS obsolete
			DESCRIPTION
				"This entry is obsolete.
				Fibre channel is not supported in Storage Management."
			::= { controllerEntry 20 }

		
		-- 1.3.6.1.4.1.674.10893.1.20.130.1.1.21
		controllerC0Port0ID OBJECT-TYPE
			SYNTAX INTEGER
			ACCESS read-only
			STATUS obsolete
			DESCRIPTION
				"This entry is obsolete.
				Fibre channel is not supported in Storage Management."
			::= { controllerEntry 21 }

		
		-- 1.3.6.1.4.1.674.10893.1.20.130.1.1.22
		controllerC0Target OBJECT-TYPE
			SYNTAX INTEGER
			ACCESS read-only
			STATUS obsolete
			DESCRIPTION
				"This entry is obsolete.
				Fibre channel is not supported in Storage Management. 
				"
			::= { controllerEntry 22 }

		
		-- 1.3.6.1.4.1.674.10893.1.20.130.1.1.23
		controllerC0Channel OBJECT-TYPE
			SYNTAX INTEGER
			ACCESS read-only
			STATUS obsolete
			DESCRIPTION
				"This entry is obsolete.
				Fibre channel is not supported in Storage Management."
			::= { controllerEntry 23 }

		
		-- 1.3.6.1.4.1.674.10893.1.20.130.1.1.24
		controllerC0OSController OBJECT-TYPE
			SYNTAX DisplayString
			ACCESS read-only
			STATUS obsolete
			DESCRIPTION
				"This entry is obsolete.
				Fibre channel is not supported in Storage Management."
			::= { controllerEntry 24 }

		
		-- 1.3.6.1.4.1.674.10893.1.20.130.1.1.25
		controllerC0BatteryState OBJECT-TYPE
			SYNTAX INTEGER
				{
				ok(1),
				failed(2),
				reconditioning(7),
				high(9),
				low(10),
				charging(12),
				missing(21)
				}
			ACCESS read-only
			STATUS obsolete
			DESCRIPTION
				"This entry is obsolete.
				Fibre channel is not supported in Storage Management. "
			::= { controllerEntry 25 }

		
		-- 1.3.6.1.4.1.674.10893.1.20.130.1.1.26
		controllerC1Port0WWN OBJECT-TYPE
			SYNTAX DisplayString
			ACCESS read-only
			STATUS obsolete
			DESCRIPTION
				"This entry is obsolete.
				Fibre channel is not supported in Storage Management."
			::= { controllerEntry 26 }

		
		-- 1.3.6.1.4.1.674.10893.1.20.130.1.1.27
		controllerC1Port0Name OBJECT-TYPE
			SYNTAX DisplayString
			ACCESS read-only
			STATUS obsolete
			DESCRIPTION
				"This entry is obsolete.
				Fibre channel is not supported in Storage Management."
			::= { controllerEntry 27 }

		
		-- 1.3.6.1.4.1.674.10893.1.20.130.1.1.28
		controllerC1Port0ID OBJECT-TYPE
			SYNTAX INTEGER
			ACCESS read-only
			STATUS obsolete
			DESCRIPTION
				"This entry is obsolete.
				Fibre channel is not supported in Storage Management."
			::= { controllerEntry 28 }

		
		-- 1.3.6.1.4.1.674.10893.1.20.130.1.1.29
		controllerC1Target OBJECT-TYPE
			SYNTAX INTEGER
			ACCESS read-only
			STATUS obsolete
			DESCRIPTION
				"This entry is obsolete.
				Fibre channel is not supported in Storage Management."
			::= { controllerEntry 29 }

		
		-- 1.3.6.1.4.1.674.10893.1.20.130.1.1.30
		controllerC1Channel OBJECT-TYPE
			SYNTAX INTEGER
			ACCESS read-only
			STATUS obsolete
			DESCRIPTION
				"This entry is obsolete.
				Fibre channel is not supported in Storage Management."
			::= { controllerEntry 30 }

		
		-- 1.3.6.1.4.1.674.10893.1.20.130.1.1.31
		controllerC1OSController OBJECT-TYPE
			SYNTAX INTEGER
			ACCESS read-only
			STATUS obsolete
			DESCRIPTION
				"This entry is obsolete.
				Fibre channel is not supported in Storage Management."
			::= { controllerEntry 31 }

		
		-- 1.3.6.1.4.1.674.10893.1.20.130.1.1.32
		controllerC1BatteryState OBJECT-TYPE
			SYNTAX INTEGER
				{
				ok(1),
				failed(2),
				reconditioning(7),
				high(9),
				low(10),
				charging(12),
				missing(21)
				}
			ACCESS read-only
			STATUS obsolete
			DESCRIPTION
				"This entry is obsolete.
				Fibre channel is not supported in Storage Management. "
			::= { controllerEntry 32 }

		
		-- 1.3.6.1.4.1.674.10893.1.20.130.1.1.33
		controllerNodeWWN OBJECT-TYPE
			SYNTAX DisplayString
			ACCESS read-only
			STATUS obsolete
			DESCRIPTION
				"This entry is obsolete.
				Fibre channel is not supported in Storage Management."
			::= { controllerEntry 33 }

		
		-- 1.3.6.1.4.1.674.10893.1.20.130.1.1.34
		controllerC0Port1WWN OBJECT-TYPE
			SYNTAX DisplayString
			ACCESS read-only
			STATUS obsolete
			DESCRIPTION
				"This entry is obsolete.
				Fibre channel is not supported in Storage Management."
			::= { controllerEntry 34 }

		
		-- 1.3.6.1.4.1.674.10893.1.20.130.1.1.35
		controllerC1Port1WWN OBJECT-TYPE
			SYNTAX DisplayString
			ACCESS read-only
			STATUS obsolete
			DESCRIPTION
				"This entry is obsolete.
				Fibre channel is not supported in Storage Management."
			::= { controllerEntry 35 }

		
		-- 1.3.6.1.4.1.674.10893.1.20.130.1.1.36
		controllerBatteryChargeCount OBJECT-TYPE
			SYNTAX INTEGER
			ACCESS read-only
			STATUS obsolete
			DESCRIPTION
				"This entry is obsolete.
				Fibre channel is not supported in Storage Management."
			::= { controllerEntry 36 }

		
		-- 1.3.6.1.4.1.674.10893.1.20.130.1.1.37
		controllerRollUpStatus OBJECT-TYPE
			SYNTAX DellStatus
			ACCESS read-only
			STATUS mandatory
			DESCRIPTION
				"Severity of the controller state.  
				This is the combined status of the controller and its components.
				Possible values:
				1: Other
				2: Unknown
				3: OK 
				4: Non-critical 
				5: Critical
				6: Non-recoverable"
			::= { controllerEntry 37 }

		
		-- 1.3.6.1.4.1.674.10893.1.20.130.1.1.38
		controllerComponentStatus OBJECT-TYPE
			SYNTAX DellStatus
			ACCESS read-only
			STATUS mandatory
			DESCRIPTION
				"The status of the controller itself without the 
				propagation of any contained component status.
				Possible values:
				1: Other
				2: Unknown
				3: OK 
				4: Non-critical 
				5: Critical
				6: Non-recoverable"
			::= { controllerEntry 38 }

		
		-- 1.3.6.1.4.1.674.10893.1.20.130.1.1.39
		controllerNexusID OBJECT-TYPE
			SYNTAX DisplayString
			ACCESS read-only
			STATUS mandatory
			DESCRIPTION
				"Durable unique ID for this controller."
			::= { controllerEntry 39 }

		
		-- 1.3.6.1.4.1.674.10893.1.20.130.1.1.40
		controllerAlarmState OBJECT-TYPE
			SYNTAX INTEGER
				{
				enabled(1),
				disabled(2),
				not-applicable(3)
				}
			ACCESS read-only
			STATUS mandatory
			DESCRIPTION
				"State, or setting for the controller's alarm.
				Possible values:
				1: Enabled
				2: Disabled
				3: Not Applicable"
			::= { controllerEntry 40 }

		
		-- 1.3.6.1.4.1.674.10893.1.20.130.1.1.41
		controllerDriverVersion OBJECT-TYPE
			SYNTAX DisplayString
			ACCESS read-only
			STATUS mandatory
			DESCRIPTION
				"Currently installed driver version for this controller."
			::= { controllerEntry 41 }

		
		-- 1.3.6.1.4.1.674.10893.1.20.130.1.1.42
		controllerPCISlot OBJECT-TYPE
			SYNTAX DisplayString
			ACCESS read-only
			STATUS mandatory
			DESCRIPTION
				"The PCI slot number or embedded number for controllers on the motherboard.
				"
			::= { controllerEntry 42 }

		
		-- 1.3.6.1.4.1.674.10893.1.20.130.1.1.43
		controllerClusterMode OBJECT-TYPE
			SYNTAX INTEGER
				{
				enabled(1),
				disabled(2),
				active(3),
				notApplicable(99)
				}
			ACCESS read-only
			STATUS mandatory
			DESCRIPTION
				"Identifies if the controller is in cluster mode.
				Possible values:
				1 : Enabled
				2 : Disabled
				3 : Active (enabled and active)
				99: Not Applicable
				"
			::= { controllerEntry 43 }

		
		-- 1.3.6.1.4.1.674.10893.1.20.130.1.1.44
		controllerMinFWVersion OBJECT-TYPE
			SYNTAX DisplayString
			ACCESS read-only
			STATUS mandatory
			DESCRIPTION
				"The minimum firmware version for Storage Management to support the controller.
				"
			::= { controllerEntry 44 }

		
		-- 1.3.6.1.4.1.674.10893.1.20.130.1.1.45
		controllerMinDriverVersion OBJECT-TYPE
			SYNTAX DisplayString
			ACCESS read-only
			STATUS mandatory
			DESCRIPTION
				"The minimum driver version for Storage Management to support the controller.
				"
			::= { controllerEntry 45 }

		
		-- 1.3.6.1.4.1.674.10893.1.20.130.1.1.46
		controllerSCSIInitiatorID OBJECT-TYPE
			SYNTAX INTEGER
			ACCESS read-only
			STATUS mandatory
			DESCRIPTION
				"The SCSI ID of the initiator."
			::= { controllerEntry 46 }

		
		-- 1.3.6.1.4.1.674.10893.1.20.130.1.1.47
		controllerChannelCount OBJECT-TYPE
			SYNTAX INTEGER
			ACCESS read-only
			STATUS mandatory
			DESCRIPTION
				"Number of channels on the controller."
			::= { controllerEntry 47 }

		
		-- 1.3.6.1.4.1.674.10893.1.20.130.1.1.48
		controllerReconstructRate OBJECT-TYPE
			SYNTAX INTEGER
			ACCESS read-only
			STATUS mandatory
			DESCRIPTION
				"The rate for reconstruct on the controller.
				"
			::= { controllerEntry 48 }

		
		-- 1.3.6.1.4.1.674.10893.1.20.130.1.1.49
		controllerPatrolReadRate OBJECT-TYPE
			SYNTAX INTEGER
			ACCESS read-only
			STATUS mandatory
			DESCRIPTION
				"The rate for patrol read on the controller.
				"
			::= { controllerEntry 49 }

		
		-- 1.3.6.1.4.1.674.10893.1.20.130.1.1.50
		controllerBGIRate OBJECT-TYPE
			SYNTAX INTEGER
			ACCESS read-only
			STATUS mandatory
			DESCRIPTION
				"The rate for background initialization on the controller.
				"
			::= { controllerEntry 50 }

		
		-- 1.3.6.1.4.1.674.10893.1.20.130.1.1.51
		controllerCheckConsistencyRate OBJECT-TYPE
			SYNTAX INTEGER
			ACCESS read-only
			STATUS mandatory
			DESCRIPTION
				"The rate for check consistency on the controller.
				"
			::= { controllerEntry 51 }

		
		-- 1.3.6.1.4.1.674.10893.1.20.130.1.1.52
		controllerPatrolReadMode OBJECT-TYPE
			SYNTAX INTEGER
				{
				automatic(1),
				manual(2),
				disabled(3)
				}
			ACCESS read-only
			STATUS mandatory
			DESCRIPTION
				"Identifies the patrol read mode.
				Possible values:
				1: Automatic (enabled)
				2: Manual (enabled)
				3: Disabled
				"
			::= { controllerEntry 52 }

		
		-- 1.3.6.1.4.1.674.10893.1.20.130.1.1.53
		controllerPatrolReadState OBJECT-TYPE
			SYNTAX INTEGER
				{
				stopped(1),
				ready(2),
				active(4),
				aborted(8)
				}
			ACCESS read-only
			STATUS mandatory
			DESCRIPTION
				"The state of the patrol read.
				1: Stopped - not running
				2: Ready - ready to start
				4: Active - is running
				8: Aborted - has aborted
				"
			::= { controllerEntry 53 }

		
		-- 1.3.6.1.4.1.674.10893.1.20.130.1.1.54
		controllerPatrolReadIterations OBJECT-TYPE
			SYNTAX INTEGER
			ACCESS read-only
			STATUS mandatory
			DESCRIPTION
				"The number of times Patrol Read has been run on this controller."
			::= { controllerEntry 54 }

		
		-- 1.3.6.1.4.1.674.10893.1.20.130.2
		channelTable OBJECT-TYPE
			SYNTAX SEQUENCE OF ChannelEntry
			ACCESS not-accessible
			STATUS mandatory
			DESCRIPTION
				"A table of controller channels. The number of entries is 
				related to the number of channels supported by a RAID 
				controller. Perc2 RAID controller supports a max of 4 
				channels per controller. The maximum number of entries is 
				implementation dependent.
				Note: The properties in this table may not be applicable to all entries."
			::= { physicalDevices 2 }

		
		-- 1.3.6.1.4.1.674.10893.1.20.130.2.1
		channelEntry OBJECT-TYPE
			SYNTAX ChannelEntry
			ACCESS not-accessible
			STATUS mandatory
			DESCRIPTION
				"An entry in the channel table. A row in this table cannot be
				created or deleted by SNMP operations on columns of the table."
			INDEX { channelNumber }
			::= { channelTable 1 }

		
		ChannelEntry ::=
			SEQUENCE { 
				channelNumber
					INTEGER,
				channelName
					DisplayString,
				channelState
					INTEGER,
				channelSeverity
					INTEGER,
				channelTermination
					INTEGER,
				channelSCSIID
					INTEGER,
				channelRollUpStatus
					DellStatus,
				channelComponentStatus
					DellStatus,
				channelNexusID
					DisplayString,
				channelDataRate
					DisplayString,
				channelBusType
					INTEGER
			 }

		-- 1.3.6.1.4.1.674.10893.1.20.130.2.1.1
		channelNumber OBJECT-TYPE
			SYNTAX INTEGER (1..255)
			ACCESS read-only
			STATUS mandatory
			DESCRIPTION
				"Instance number of this channel entry."
			::= { channelEntry 1 }

		
		-- 1.3.6.1.4.1.674.10893.1.20.130.2.1.2
		channelName OBJECT-TYPE
			SYNTAX DisplayString
			ACCESS read-only
			STATUS mandatory
			DESCRIPTION
				"The name of the channel as represented in Storage Management.  
				The name will include the word channel and the instance.  
				For example: Channel 1"
			::= { channelEntry 2 }

		
		-- 1.3.6.1.4.1.674.10893.1.20.130.2.1.3
		channelState OBJECT-TYPE
			SYNTAX INTEGER
				{
				ready(1),
				failed(2),
				online(3),
				offline(4),
				degraded(6)
				}
			ACCESS read-only
			STATUS mandatory
			DESCRIPTION
				"The current condition of the channel.
				Possible states:
				0: Unknown
				1: Ready - The I/O has resumed.
				2: Failed 
				3: Online
				4: Offline - The I/O has paused.
				6: Degraded
				"
			::= { channelEntry 3 }

		
		-- 1.3.6.1.4.1.674.10893.1.20.130.2.1.4
		channelSeverity OBJECT-TYPE
			SYNTAX INTEGER
				{
				warning(1),
				error(2),
				failure(3)
				}
			ACCESS read-only
			STATUS obsolete
			DESCRIPTION
				"This entry is obsolete for Storage Management.
				It was replaced with RollUpStatus and ComponentStatus for each device."
			::= { channelEntry 4 }

		
		-- 1.3.6.1.4.1.674.10893.1.20.130.2.1.5
		channelTermination OBJECT-TYPE
			SYNTAX INTEGER
				{
				wide(1),
				narrow(2),
				notTerminated(3)
				}
			ACCESS read-only
			STATUS mandatory
			DESCRIPTION
				"The type of SCSI termination on this channel.  
				Termination is required for proper operation of this channel.
				
				1: Wide Termination (16 bit)
				2: Narrow Termination (8 bit)
				3: Not Terminated"
			::= { channelEntry 5 }

		
		-- 1.3.6.1.4.1.674.10893.1.20.130.2.1.6
		channelSCSIID OBJECT-TYPE
			SYNTAX INTEGER
			ACCESS read-only
			STATUS mandatory
			DESCRIPTION
				"The SCSI ID of the controller to which the channel belongs."
			::= { channelEntry 6 }

		
		-- 1.3.6.1.4.1.674.10893.1.20.130.2.1.7
		channelRollUpStatus OBJECT-TYPE
			SYNTAX DellStatus
			ACCESS read-only
			STATUS mandatory
			DESCRIPTION
				"Severity of the channel state.
				This is the combined status of the channel and its 
				components.
				Possible values:
				1: Other
				2: Unknown
				3: OK 
				4: Non-critical 
				5: Critical
				6: Non-recoverable"
			::= { channelEntry 7 }

		
		-- 1.3.6.1.4.1.674.10893.1.20.130.2.1.8
		channelComponentStatus OBJECT-TYPE
			SYNTAX DellStatus
			ACCESS read-only
			STATUS mandatory
			DESCRIPTION
				"The status of the channel itself with out without the 
				propagation of any contained component status.
				Possible values:
				1: Other
				2: Unknown
				3: OK 
				4: Non-critical 
				5: Critical
				6: Non-recoverable"
			::= { channelEntry 8 }

		
		-- 1.3.6.1.4.1.674.10893.1.20.130.2.1.9
		channelNexusID OBJECT-TYPE
			SYNTAX DisplayString
			ACCESS read-only
			STATUS mandatory
			DESCRIPTION
				"Durable unique ID for this channel."
			::= { channelEntry 9 }

		
		-- 1.3.6.1.4.1.674.10893.1.20.130.2.1.10
		channelDataRate OBJECT-TYPE
			SYNTAX DisplayString
			ACCESS read-only
			STATUS mandatory
			DESCRIPTION
				"The data rate (SCSI speed) of the channel. Example: Ultra 320M SCSI"
			::= { channelEntry 10 }

		
		-- 1.3.6.1.4.1.674.10893.1.20.130.2.1.11
		channelBusType OBJECT-TYPE
			SYNTAX INTEGER
				{
				scsi(1),
				ide(2),
				fibreChannel(3),
				ssa(4),
				usb(6),
				sata(7),
				sas(8)
				}
			ACCESS read-only
			STATUS mandatory
			DESCRIPTION
				"The bus type of the channel.
				Possible values:
				1: SCSI
				2: IDE
				3: Fibre Channel
				4: SSA
				6: USB
				7: SATA
				8: SAS"
			::= { channelEntry 11 }

		
		-- 1.3.6.1.4.1.674.10893.1.20.130.3
		enclosureTable OBJECT-TYPE
			SYNTAX SEQUENCE OF EnclosureEntry
			ACCESS not-accessible
			STATUS mandatory
			DESCRIPTION
				"A table of managed Enclosures. The number of entries is 
				related to number of enclosures discovered in the system.
				The maximum number of entries is implementation dependent.
				Note: The properties in this table may not be applicable to all entries."
			::= { physicalDevices 3 }

		
		-- 1.3.6.1.4.1.674.10893.1.20.130.3.1
		enclosureEntry OBJECT-TYPE
			SYNTAX EnclosureEntry
			ACCESS not-accessible
			STATUS mandatory
			DESCRIPTION
				"An entry in the Enclosure table . A row in this table cannot be
				created or deleted by SNMP operations on columns of the table."
			INDEX { enclosureNumber }
			::= { enclosureTable 1 }

		
		EnclosureEntry ::=
			SEQUENCE { 
				enclosureNumber
					INTEGER,
				enclosureName
					DisplayString,
				enclosureVendor
					DisplayString,
				enclosureState
					INTEGER,
				enclosureSeverity
					INTEGER,
				enclosureID
					INTEGER,
				enclosureProcessorVersion
					DisplayString,
				enclosureServiceTag
					DisplayString,
				enclosureAssetTag
					DisplayString,
				enclosureAssetName
					DisplayString,
				enclosureSplitBusPartNumber
					DisplayString,
				enclosureProductID
					DisplayString,
				enclosureKernelVersion
					DisplayString,
				enclosureESM1PartNumber
					DisplayString,
				enclosureESM2PartNumber
					DisplayString,
				enclosureType
					INTEGER,
				enclosureProcessor2Version
					DisplayString,
				enclosureConfig
					INTEGER,
				enclosureChannelNumber
					INTEGER,
				enclosureAlarm
					INTEGER,
				enclosureBackplanePartNumber
					DisplayString,
				enclosureSCSIID
					INTEGER,
				enclosureRollUpStatus
					DellStatus,
				enclosureComponentStatus
					DellStatus,
				enclosureNexusID
					DisplayString,
				enclosureFirmwareVersion
					DisplayString,
				enclosureSCSIRate
					DisplayString,
				enclosurePartNumber
					DisplayString,
				enclosureSerialNumber
					DisplayString,
				enclosureSASAddress
					DisplayString
			 }

		-- 1.3.6.1.4.1.674.10893.1.20.130.3.1.1
		enclosureNumber OBJECT-TYPE
			SYNTAX INTEGER (1..255)
			ACCESS read-only
			STATUS mandatory
			DESCRIPTION
				"Instance number of the enclosure entry."
			::= { enclosureEntry 1 }

		
		-- 1.3.6.1.4.1.674.10893.1.20.130.3.1.2
		enclosureName OBJECT-TYPE
			SYNTAX DisplayString
			ACCESS read-only
			STATUS mandatory
			DESCRIPTION
				"The enclosure's name as represented in Storage Management."
			::= { enclosureEntry 2 }

		
		-- 1.3.6.1.4.1.674.10893.1.20.130.3.1.3
		enclosureVendor OBJECT-TYPE
			SYNTAX DisplayString
			ACCESS read-only
			STATUS mandatory
			DESCRIPTION
				"The enclosure's (re)seller's name."
			::= { enclosureEntry 3 }

		
		-- 1.3.6.1.4.1.674.10893.1.20.130.3.1.4
		enclosureState OBJECT-TYPE
			SYNTAX INTEGER
				{
				ready(1),
				failed(2),
				online(3),
				offline(4),
				degraded(6)
				}
			ACCESS read-only
			STATUS mandatory
			DESCRIPTION
				"The current condition of the enclosure
				(which includes any devices connected to it.)
				Possible states:
				0: Unknown
				1: Ready
				2: Failed
				3: Online
				4: Offline
				6: Degraded"
			::= { enclosureEntry 4 }

		
		-- 1.3.6.1.4.1.674.10893.1.20.130.3.1.5
		enclosureSeverity OBJECT-TYPE
			SYNTAX INTEGER
				{
				warning(1),
				error(2),
				failure(3)
				}
			ACCESS read-only
			STATUS obsolete
			DESCRIPTION
				"This entry is obsolete for Storage Management.
				It was replaced with RollUpStatus and ComponentStatus for each device."
			::= { enclosureEntry 5 }

		
		-- 1.3.6.1.4.1.674.10893.1.20.130.3.1.6
		enclosureID OBJECT-TYPE
			SYNTAX INTEGER
			ACCESS read-only
			STATUS mandatory
			DESCRIPTION
				"The SCSI address of the processor."
			::= { enclosureEntry 6 }

		
		-- 1.3.6.1.4.1.674.10893.1.20.130.3.1.7
		enclosureProcessorVersion OBJECT-TYPE
			SYNTAX DisplayString
			ACCESS read-only
			STATUS obsolete
			DESCRIPTION
				"This entry is obsolete for Storage Management."
			::= { enclosureEntry 7 }

		
		-- 1.3.6.1.4.1.674.10893.1.20.130.3.1.8
		enclosureServiceTag OBJECT-TYPE
			SYNTAX DisplayString
			ACCESS read-only
			STATUS mandatory
			DESCRIPTION
				"Enclosure identification used when consulting customer support."
			::= { enclosureEntry 8 }

		
		-- 1.3.6.1.4.1.674.10893.1.20.130.3.1.9
		enclosureAssetTag OBJECT-TYPE
			SYNTAX DisplayString
			ACCESS read-only
			STATUS mandatory
			DESCRIPTION
				"User definable asset tag for the enclosure."
			::= { enclosureEntry 9 }

		
		-- 1.3.6.1.4.1.674.10893.1.20.130.3.1.10
		enclosureAssetName OBJECT-TYPE
			SYNTAX DisplayString
			ACCESS read-only
			STATUS mandatory
			DESCRIPTION
				"User definable asset name of the enclosure."
			::= { enclosureEntry 10 }

		
		-- 1.3.6.1.4.1.674.10893.1.20.130.3.1.11
		enclosureSplitBusPartNumber OBJECT-TYPE
			SYNTAX DisplayString
			ACCESS read-only
			STATUS mandatory
			DESCRIPTION
				"The enclosure's split bus part number."
			::= { enclosureEntry 11 }

		
		-- 1.3.6.1.4.1.674.10893.1.20.130.3.1.12
		enclosureProductID OBJECT-TYPE
			SYNTAX DisplayString
			ACCESS read-only
			STATUS mandatory
			DESCRIPTION
				"The enclosure's product identification.  This also corresponds to the enclosure type.  
				"
			::= { enclosureEntry 12 }

		
		-- 1.3.6.1.4.1.674.10893.1.20.130.3.1.13
		enclosureKernelVersion OBJECT-TYPE
			SYNTAX DisplayString
			ACCESS read-only
			STATUS obsolete
			DESCRIPTION
				"This entry is obsolete for Storage Management.
				Refer to enclosureFirmwareVersion for the firmware version of the enclosure."
			::= { enclosureEntry 13 }

		
		-- 1.3.6.1.4.1.674.10893.1.20.130.3.1.14
		enclosureESM1PartNumber OBJECT-TYPE
			SYNTAX DisplayString
			ACCESS read-only
			STATUS obsolete
			DESCRIPTION
				"This entry is obsolete for Storage Management."
			::= { enclosureEntry 14 }

		
		-- 1.3.6.1.4.1.674.10893.1.20.130.3.1.15
		enclosureESM2PartNumber OBJECT-TYPE
			SYNTAX DisplayString
			ACCESS read-only
			STATUS obsolete
			DESCRIPTION
				"This entry is obsolete for Storage Management."
			::= { enclosureEntry 15 }

		
		-- 1.3.6.1.4.1.674.10893.1.20.130.3.1.16
		enclosureType OBJECT-TYPE
			SYNTAX INTEGER
				{
				internal(1),
				dELLPV200SPV201S(2),
				dELLPV210SPV211S(3),
				dELLPV220SPV221S(4),
				dELLPV660F(5),
				dELLPV224F(6),
				dELLPV660F224F(7),
				md1000(8)
				}
			ACCESS read-only
			STATUS mandatory
			DESCRIPTION
				"The type of this enclosure.
				Possible values:
				1: Internal
				2: Dell PV200S (PV201S)
				3: Dell PV210S (PV211S)
				4: Dell PV220S (PV221S)
				5: Dell PV660F
				6: Dell PV224F
				7: Dell PV660F / PV224F
				8: Dell MD1000
				9: Dell MD1120"
			::= { enclosureEntry 16 }

		
		-- 1.3.6.1.4.1.674.10893.1.20.130.3.1.17
		enclosureProcessor2Version OBJECT-TYPE
			SYNTAX DisplayString
			ACCESS read-only
			STATUS mandatory
			DESCRIPTION
				"This entry is obsolete for Storage Management."
			::= { enclosureEntry 17 }

		
		-- 1.3.6.1.4.1.674.10893.1.20.130.3.1.18
		enclosureConfig OBJECT-TYPE
			SYNTAX INTEGER
				{
				joined(1),
				splitBus(2),
				clustered(3),
				unified(4)
				}
			ACCESS read-only
			STATUS mandatory
			DESCRIPTION
				"The current configuration of the enclosure's backplane.
				Possible values:
				1: Joined
				2: Split Bus
				3: Clustered
				4: Unified"
			::= { enclosureEntry 18 }

		
		-- 1.3.6.1.4.1.674.10893.1.20.130.3.1.19
		enclosureChannelNumber OBJECT-TYPE
			SYNTAX INTEGER
			ACCESS read-only
			STATUS mandatory
			DESCRIPTION
				"The channel number, or bus, to which the enclosure is connected."
			::= { enclosureEntry 19 }

		
		-- 1.3.6.1.4.1.674.10893.1.20.130.3.1.20
		enclosureAlarm OBJECT-TYPE
			SYNTAX INTEGER
				{
				disabled(1),
				enabled(2)
				}
			ACCESS read-only
			STATUS mandatory
			DESCRIPTION
				"The current status of the enclosure's alarm (PV220S, and PV221S only.)
				Possible values:
				1: Disabled
				2: Enabled"
			::= { enclosureEntry 20 }

		
		-- 1.3.6.1.4.1.674.10893.1.20.130.3.1.21
		enclosureBackplanePartNumber OBJECT-TYPE
			SYNTAX DisplayString
			ACCESS read-only
			STATUS mandatory
			DESCRIPTION
				"The part number of the enclosure's backplane."
			::= { enclosureEntry 21 }

		
		-- 1.3.6.1.4.1.674.10893.1.20.130.3.1.22
		enclosureSCSIID OBJECT-TYPE
			SYNTAX INTEGER
			ACCESS read-only
			STATUS mandatory
			DESCRIPTION
				"The SCSI ID of the controller to which this enclosure is attached."
			::= { enclosureEntry 22 }

		
		-- 1.3.6.1.4.1.674.10893.1.20.130.3.1.23
		enclosureRollUpStatus OBJECT-TYPE
			SYNTAX DellStatus
			ACCESS read-only
			STATUS mandatory
			DESCRIPTION
				"Severity of the enclosure state.
				This is the combined status of the enclosure and its components.
				Possible values:
				1: Other
				2: Unknown
				3: OK 
				4: Non-critical 
				5: Critical
				6: Non-recoverable"
			::= { enclosureEntry 23 }

		
		-- 1.3.6.1.4.1.674.10893.1.20.130.3.1.24
		enclosureComponentStatus OBJECT-TYPE
			SYNTAX DellStatus
			ACCESS read-only
			STATUS mandatory
			DESCRIPTION
				"The status of the enclosure itself without the 
				propagation of any contained component status.
				Possible values:
				1: Other
				2: Unknown
				3: OK 
				4: Non-critical 
				5: Critical
				6: Non-recoverable"
			::= { enclosureEntry 24 }

		
		-- 1.3.6.1.4.1.674.10893.1.20.130.3.1.25
		enclosureNexusID OBJECT-TYPE
			SYNTAX DisplayString
			ACCESS read-only
			STATUS mandatory
			DESCRIPTION
				"Durable unique ID for this enclosure."
			::= { enclosureEntry 25 }

		
		-- 1.3.6.1.4.1.674.10893.1.20.130.3.1.26
		enclosureFirmwareVersion OBJECT-TYPE
			SYNTAX DisplayString
			ACCESS read-only
			STATUS mandatory
			DESCRIPTION
				"The firmware version of the enclosure."
			::= { enclosureEntry 26 }

		
		-- 1.3.6.1.4.1.674.10893.1.20.130.3.1.27
		enclosureSCSIRate OBJECT-TYPE
			SYNTAX DisplayString
			ACCESS read-only
			STATUS mandatory
			DESCRIPTION
				"Actual SCSI rate in the enclosure.
				"
			::= { enclosureEntry 27 }

		
		-- 1.3.6.1.4.1.674.10893.1.20.130.3.1.28
		enclosurePartNumber OBJECT-TYPE
			SYNTAX DisplayString
			ACCESS read-only
			STATUS mandatory
			DESCRIPTION
				"The part number of the enclosure.
				"
			::= { enclosureEntry 28 }

		
		-- 1.3.6.1.4.1.674.10893.1.20.130.3.1.29
		enclosureSerialNumber OBJECT-TYPE
			SYNTAX DisplayString
			ACCESS read-only
			STATUS mandatory
			DESCRIPTION
				"Serial number of the enclosure.
				"
			::= { enclosureEntry 29 }

		
		-- 1.3.6.1.4.1.674.10893.1.20.130.3.1.30
		enclosureSASAddress OBJECT-TYPE
			SYNTAX DisplayString
			ACCESS read-only
			STATUS mandatory
			DESCRIPTION
				"The specified SAS address if this is a SAS enclosure. "
			::= { enclosureEntry 30 }

		
		-- 1.3.6.1.4.1.674.10893.1.20.130.4
		arrayDiskTable OBJECT-TYPE
			SYNTAX SEQUENCE OF ArrayDiskEntry
			ACCESS not-accessible
			STATUS mandatory
			DESCRIPTION
				"A table of managed Array Disks. The number of entries is 
				related to number of Array Disks discovered in the system.
				The maximum number of entries is implementation dependent.
				Note: The properties in this table may not be applicable to all entries."
			::= { physicalDevices 4 }

		
		-- 1.3.6.1.4.1.674.10893.1.20.130.4.1
		arrayDiskEntry OBJECT-TYPE
			SYNTAX ArrayDiskEntry
			ACCESS not-accessible
			STATUS mandatory
			DESCRIPTION
				"An entry in the Array Disk table . A row in this table cannot be
				created or deleted by SNMP operations on columns of the table."
			INDEX { arrayDiskNumber }
			::= { arrayDiskTable 1 }

		
		ArrayDiskEntry ::=
			SEQUENCE { 
				arrayDiskNumber
					INTEGER,
				arrayDiskName
					DisplayString,
				arrayDiskVendor
					DisplayString,
				arrayDiskState
					INTEGER,
				arrayDiskSeverity
					INTEGER,
				arrayDiskProductID
					DisplayString,
				arrayDiskSerialNo
					DisplayString,
				arrayDiskRevision
					DisplayString,
				arrayDiskEnclosureID
					DisplayString,
				arrayDiskChannel
					INTEGER,
				arrayDiskLengthInMB
					INTEGER,
				arrayDiskLengthInBytes
					INTEGER,
				arrayDiskLargestContiguousFreeSpaceInMB
					INTEGER,
				arrayDiskLargestContiguousFreeSpaceInBytes
					INTEGER,
				arrayDiskTargetID
					INTEGER,
				arrayDiskLunID
					INTEGER,
				arrayDiskUsedSpaceInMB
					INTEGER,
				arrayDiskUsedSpaceInBytes
					INTEGER,
				arrayDiskFreeSpaceInMB
					INTEGER,
				arrayDiskFreeSpaceInBytes
					INTEGER,
				arrayDiskBusType
					INTEGER,
				arrayDiskSpareState
					INTEGER,
				arrayDiskRollUpStatus
					DellStatus,
				arrayDiskComponentStatus
					DellStatus,
				arrayDiskDeviceName
					DisplayString,
				arrayDiskNexusID
					DisplayString,
				arrayDiskPartNumber
					DisplayString,
				arrayDiskSASAddress
					DisplayString,
				arrayDiskNegotiatedSpeed
					INTEGER,
				arrayDiskCapableSpeed
					INTEGER,
				arrayDiskSmartAlertIndication
					INTEGER,
				arrayDiskManufactureDay
					DisplayString,
				arrayDiskManufactureWeek
					DisplayString,
				arrayDiskManufactureYear
					DisplayString,
				arrayDiskMediaType
					INTEGER
			 }

		-- 1.3.6.1.4.1.674.10893.1.20.130.4.1.1
		arrayDiskNumber OBJECT-TYPE
			SYNTAX INTEGER (1..1000000000)
			ACCESS read-only
			STATUS mandatory
			DESCRIPTION
				"Instance number of this array disk entry."
			::= { arrayDiskEntry 1 }

		
		-- 1.3.6.1.4.1.674.10893.1.20.130.4.1.2
		arrayDiskName OBJECT-TYPE
			SYNTAX DisplayString
			ACCESS read-only
			STATUS mandatory
			DESCRIPTION
				"The name of the array disk as represented in Storage Management."
			::= { arrayDiskEntry 2 }

		
		-- 1.3.6.1.4.1.674.10893.1.20.130.4.1.3
		arrayDiskVendor OBJECT-TYPE
			SYNTAX DisplayString
			ACCESS read-only
			STATUS mandatory
			DESCRIPTION
				"The array disk's manufacturer's name."
			::= { arrayDiskEntry 3 }

		
		-- 1.3.6.1.4.1.674.10893.1.20.130.4.1.4
		arrayDiskState OBJECT-TYPE
			SYNTAX INTEGER
				{
				ready(1),
				failed(2),
				online(3),
				offline(4),
				degraded(6),
				recovering(7),
				removed(11),
				resynching(15),
				rebuild(24),
				noMedia(25),
				formatting(26),
				diagnostics(28),
				predictiveFailure(34),
				initializing(35),
				foreign(39),
				clear(40),
				unsupported(41),
				incompatible(53)
				}
			ACCESS read-only
			STATUS mandatory
			DESCRIPTION
				"The current condition of the array disk.
				Possible states:
				 0: Unknown
				 1: Ready - Available for use, but no RAID configuration has been assigned. 
				 2: Failed - Not operational.
				 3: Online - Operational. RAID configuration has been assigned.
				 4: Offline - The drive is not available to the RAID controller. 
				 6: Degraded - Refers to a fault-tolerant array/virtual disk that has a failed disk. 
				 7: Recovering - Refers to state of recovering from bad blocks on disks. 
				11: Removed - Indicates that array disk has been removed. 
				15: Resynching - Indicates one of the following types of disk operations: Transform Type, Reconfiguration, and Check Consistency. 
				24: Rebuild
				25: No Media - CD-ROM or removable disk has no media. 
				26: Formatting - In the process of formatting. 
				28: Diagnostics - Diagnostics are running. 
				34: Predictive failure
				35: Initializing: Applies only to virtual disks on PERC, PERC 2/SC, and PERC 2/DC controllers.
				39: Foreign
				40: Clear
				41: Unsupported
				53: Incompatible
				
				"
			::= { arrayDiskEntry 4 }

		
		-- 1.3.6.1.4.1.674.10893.1.20.130.4.1.5
		arrayDiskSeverity OBJECT-TYPE
			SYNTAX INTEGER
				{
				warning(1),
				error(2),
				failure(3)
				}
			ACCESS read-only
			STATUS obsolete
			DESCRIPTION
				"This entry is obsolete for Storage Management.
				It was replaced with RollUpStatus and ComponentStatus for each device."
			::= { arrayDiskEntry 5 }

		
		-- 1.3.6.1.4.1.674.10893.1.20.130.4.1.6
		arrayDiskProductID OBJECT-TYPE
			SYNTAX DisplayString
			ACCESS read-only
			STATUS mandatory
			DESCRIPTION
				"The model number of the array disk."
			::= { arrayDiskEntry 6 }

		
		-- 1.3.6.1.4.1.674.10893.1.20.130.4.1.7
		arrayDiskSerialNo OBJECT-TYPE
			SYNTAX DisplayString
			ACCESS read-only
			STATUS mandatory
			DESCRIPTION
				"The array disk's unique identification number from the manufacturer.
				"
			::= { arrayDiskEntry 7 }

		
		-- 1.3.6.1.4.1.674.10893.1.20.130.4.1.8
		arrayDiskRevision OBJECT-TYPE
			SYNTAX DisplayString
			ACCESS read-only
			STATUS mandatory
			DESCRIPTION
				"The firmware version of the array disk."
			::= { arrayDiskEntry 8 }

		
		-- 1.3.6.1.4.1.674.10893.1.20.130.4.1.9
		arrayDiskEnclosureID OBJECT-TYPE
			SYNTAX DisplayString
			ACCESS read-only
			STATUS mandatory
			DESCRIPTION
				"The SCSI ID of the enclosure processor to which this array disk belongs."
			::= { arrayDiskEntry 9 }

		
		-- 1.3.6.1.4.1.674.10893.1.20.130.4.1.10
		arrayDiskChannel OBJECT-TYPE
			SYNTAX INTEGER
			ACCESS read-only
			STATUS mandatory
			DESCRIPTION
				"The bus to which this array disk is connected."
			::= { arrayDiskEntry 10 }

		
		-- 1.3.6.1.4.1.674.10893.1.20.130.4.1.11
		arrayDiskLengthInMB OBJECT-TYPE
			SYNTAX INTEGER
			ACCESS read-only
			STATUS mandatory
			DESCRIPTION
				"The size in megabytes of the array disk.  If this size is 0, it is smaller than a megabyte."
			::= { arrayDiskEntry 11 }

		
		-- 1.3.6.1.4.1.674.10893.1.20.130.4.1.12
		arrayDiskLengthInBytes OBJECT-TYPE
			SYNTAX INTEGER
			ACCESS read-only
			STATUS mandatory
			DESCRIPTION
				"The size of the array disk in bytes that is less than 
				a megabyte.  This size plus the arrayDiskLengthInMB is
				the total size of the array disk."
			::= { arrayDiskEntry 12 }

		
		-- 1.3.6.1.4.1.674.10893.1.20.130.4.1.13
		arrayDiskLargestContiguousFreeSpaceInMB OBJECT-TYPE
			SYNTAX INTEGER
			ACCESS read-only
			STATUS mandatory
			DESCRIPTION
				"The size in megabytes of the largest contiguous free space
				on the array disk.  If this size is 0, it is less than a megabyte."
			::= { arrayDiskEntry 13 }

		
		-- 1.3.6.1.4.1.674.10893.1.20.130.4.1.14
		arrayDiskLargestContiguousFreeSpaceInBytes OBJECT-TYPE
			SYNTAX INTEGER
			ACCESS read-only
			STATUS mandatory
			DESCRIPTION
				"The size of the largest contiguous free space on this
				array disk in bytes that is less than a megabyte.  
				This size plus the arrayDiskLargestContiguousFreeSpaceInMB
				is the total size of the largest contiguous free space on 
				the array disk."
			::= { arrayDiskEntry 14 }

		
		-- 1.3.6.1.4.1.674.10893.1.20.130.4.1.15
		arrayDiskTargetID OBJECT-TYPE
			SYNTAX INTEGER (0..15)
			ACCESS read-only
			STATUS mandatory
			DESCRIPTION
				"The SCSI target ID which this array disk is assigned.  "
			::= { arrayDiskEntry 15 }

		
		-- 1.3.6.1.4.1.674.10893.1.20.130.4.1.16
		arrayDiskLunID OBJECT-TYPE
			SYNTAX INTEGER
			ACCESS read-only
			STATUS mandatory
			DESCRIPTION
				"The array disk's logical unit number. "
			::= { arrayDiskEntry 16 }

		
		-- 1.3.6.1.4.1.674.10893.1.20.130.4.1.17
		arrayDiskUsedSpaceInMB OBJECT-TYPE
			SYNTAX INTEGER
			ACCESS read-only
			STATUS mandatory
			DESCRIPTION
				"The amount in megabytes of the used space on the array
				disk.  If this size is 0, it is smaller than a megabyte."
			::= { arrayDiskEntry 17 }

		
		-- 1.3.6.1.4.1.674.10893.1.20.130.4.1.18
		arrayDiskUsedSpaceInBytes OBJECT-TYPE
			SYNTAX INTEGER
			ACCESS read-only
			STATUS mandatory
			DESCRIPTION
				"The size in bytes of the used space on the array disk
				that is smaller than a megabyte.  This size plus the 
				arrayDiskUsedSpaceInMB is the total amount of used space
				on the array disk."
			::= { arrayDiskEntry 18 }

		
		-- 1.3.6.1.4.1.674.10893.1.20.130.4.1.19
		arrayDiskFreeSpaceInMB OBJECT-TYPE
			SYNTAX INTEGER
			ACCESS read-only
			STATUS mandatory
			DESCRIPTION
				"The amount in megabytes of the free space on the array
				disk.  If this size is 0, it is smaller than a megabyte."
			::= { arrayDiskEntry 19 }

		
		-- 1.3.6.1.4.1.674.10893.1.20.130.4.1.20
		arrayDiskFreeSpaceInBytes OBJECT-TYPE
			SYNTAX INTEGER
			ACCESS read-only
			STATUS mandatory
			DESCRIPTION
				"The size in bytes of the free space on the array disk
				that is smaller than a megabyte.  This size plus the 
				arrayDiskFreeSpaceInMB is the total amount of free space
				on the array disk."
			::= { arrayDiskEntry 20 }

		
		-- 1.3.6.1.4.1.674.10893.1.20.130.4.1.21
		arrayDiskBusType OBJECT-TYPE
			SYNTAX INTEGER
				{
				scsi(1),
				ide(2),
				fibre(3),
				ssa(4),
				usb(6),
				sata(7),
				sas(8)
				}
			ACCESS read-only
			STATUS mandatory
			DESCRIPTION
				"The bus type of the array disk.
				Possible values:
				1: SCSI
				2: IDE
				3: Fibre Channel
				4: SSA
				6: USB
				7: SATA
				8: SAS"
			::= { arrayDiskEntry 21 }

		
		-- 1.3.6.1.4.1.674.10893.1.20.130.4.1.22
		arrayDiskSpareState OBJECT-TYPE
			SYNTAX INTEGER
				{
				memberVD(1),
				memberDG(2),
				globalHotSpare(3),
				dedicatedHotSpare(4),
				notASpare(5),
				notApplicable(99)
				}
			ACCESS read-only
			STATUS mandatory
			DESCRIPTION
				"The status of the array disk as a spare.
				Possible states:
				1 : disk is a member of a virtual disk
				2 : disk is a member of a disk group
				3 : disk is a global hot spare
				4 : disk is a dedicated hot spare
				5 : not a spare
				99: not applicable"
			::= { arrayDiskEntry 22 }

		
		-- 1.3.6.1.4.1.674.10893.1.20.130.4.1.23
		arrayDiskRollUpStatus OBJECT-TYPE
			SYNTAX DellStatus
			ACCESS read-only
			STATUS mandatory
			DESCRIPTION
				"Severity of the array disk state.
				This is the combined status of the array disk and its components.
				Possible values:
				1: Other
				2: Unknown
				3: OK 
				4: Non-critical 
				5: Critical
				6: Non-recoverable"
			::= { arrayDiskEntry 23 }

		
		-- 1.3.6.1.4.1.674.10893.1.20.130.4.1.24
		arrayDiskComponentStatus OBJECT-TYPE
			SYNTAX DellStatus
			ACCESS read-only
			STATUS mandatory
			DESCRIPTION
				"The status of the array disk itself without the 
				propagation of any contained component status.
				Possible values:
				1: Other
				2: Unknown
				3: OK 
				4: Non-critical 
				5: Critical
				6: Non-recoverable"
			::= { arrayDiskEntry 24 }

		
		-- 1.3.6.1.4.1.674.10893.1.20.130.4.1.25
		arrayDiskDeviceName OBJECT-TYPE
			SYNTAX DisplayString
			ACCESS read-only
			STATUS mandatory
			DESCRIPTION
				"The operating system device name for this disk. This property is only applicable to array disks attached to a RAID controller."
			::= { arrayDiskEntry 25 }

		
		-- 1.3.6.1.4.1.674.10893.1.20.130.4.1.26
		arrayDiskNexusID OBJECT-TYPE
			SYNTAX DisplayString
			ACCESS read-only
			STATUS mandatory
			DESCRIPTION
				"Durable unique ID for this array disk."
			::= { arrayDiskEntry 26 }

		
		-- 1.3.6.1.4.1.674.10893.1.20.130.4.1.27
		arrayDiskPartNumber OBJECT-TYPE
			SYNTAX DisplayString
			ACCESS read-only
			STATUS mandatory
			DESCRIPTION
				"The part number of the disk.
				"
			::= { arrayDiskEntry 27 }

		
		-- 1.3.6.1.4.1.674.10893.1.20.130.4.1.28
		arrayDiskSASAddress OBJECT-TYPE
			SYNTAX DisplayString
			ACCESS read-only
			STATUS mandatory
			DESCRIPTION
				"The specified SAS address if this is a SAS disk.
				"
			::= { arrayDiskEntry 28 }

		
		-- 1.3.6.1.4.1.674.10893.1.20.130.4.1.29
		arrayDiskNegotiatedSpeed OBJECT-TYPE
			SYNTAX INTEGER
			ACCESS read-only
			STATUS mandatory
			DESCRIPTION
				"The speed at which the drive is actually running in MPS (megabytes per second).
				"
			::= { arrayDiskEntry 29 }

		
		-- 1.3.6.1.4.1.674.10893.1.20.130.4.1.30
		arrayDiskCapableSpeed OBJECT-TYPE
			SYNTAX INTEGER
			ACCESS read-only
			STATUS mandatory
			DESCRIPTION
				"The maximum speed at which the drive is capable of negotiating in MPS (megabytes per second).
				"
			::= { arrayDiskEntry 30 }

		
		-- 1.3.6.1.4.1.674.10893.1.20.130.4.1.31
		arrayDiskSmartAlertIndication OBJECT-TYPE
			SYNTAX INTEGER
				{
				no(1),
				yes(2)
				}
			ACCESS read-only
			STATUS mandatory
			DESCRIPTION
				"Indicated whether the disk has received a predictive failure.
				Possible values:
				1: No - disk has not received a predictive failure alert
				2: Yes - disk has received a predictive failure alert"
			::= { arrayDiskEntry 31 }

		
		-- 1.3.6.1.4.1.674.10893.1.20.130.4.1.32
		arrayDiskManufactureDay OBJECT-TYPE
			SYNTAX DisplayString
			ACCESS read-only
			STATUS mandatory
			DESCRIPTION
				"The day of the week (1=Sunday thru 7=Saturday) on which this disk was manufactured."
			::= { arrayDiskEntry 32 }

		
		-- 1.3.6.1.4.1.674.10893.1.20.130.4.1.33
		arrayDiskManufactureWeek OBJECT-TYPE
			SYNTAX DisplayString
			ACCESS read-only
			STATUS mandatory
			DESCRIPTION
				"The week (1 thru 53) in which this disk was manufactured."
			::= { arrayDiskEntry 33 }

		
		-- 1.3.6.1.4.1.674.10893.1.20.130.4.1.34
		arrayDiskManufactureYear OBJECT-TYPE
			SYNTAX DisplayString
			ACCESS read-only
			STATUS mandatory
			DESCRIPTION
				"The four digit year in which this disk was manufactured."
			::= { arrayDiskEntry 34 }

		
		-- 1.3.6.1.4.1.674.10893.1.20.130.4.1.35
		arrayDiskMediaType OBJECT-TYPE
			SYNTAX INTEGER
				{
				unknown(1),
				hdd(2),
				ssd(3)
				}
			ACCESS read-only
			STATUS mandatory
			DESCRIPTION
				"The Media type of the array disk.
				Possible Values:
				1:unknown
				2:hdd
				3:ssd"
			::= { arrayDiskEntry 35 }

		
		-- 1.3.6.1.4.1.674.10893.1.20.130.5
		arrayDiskEnclosureConnectionTable OBJECT-TYPE
			SYNTAX SEQUENCE OF ArrayDiskEnclosureConnectionEntry
			ACCESS not-accessible
			STATUS mandatory
			DESCRIPTION
				"A table of the connections between array disks, their enclosure, 
				and their associated controller.  For each object in the table, its
				object number corresponds to an instance number in the appropriate 
				MIB table for that object where all of the object properties can be found.
				Note: Only array disks that are part of an enclosure will be listed
				in this table.  Backplanes are considered enclosures by
				Storage Management."
			::= { physicalDevices 5 }

		
		-- 1.3.6.1.4.1.674.10893.1.20.130.5.1
		arrayDiskEnclosureConnectionEntry OBJECT-TYPE
			SYNTAX ArrayDiskEnclosureConnectionEntry
			ACCESS not-accessible
			STATUS mandatory
			DESCRIPTION
				"An entry in the Array Disk Enclosure Connection table . A row in this table cannot be
				created or deleted by SNMP operations on columns of the table."
			INDEX { arrayDiskEnclosureConnectionNumber }
			::= { arrayDiskEnclosureConnectionTable 1 }

		
		ArrayDiskEnclosureConnectionEntry ::=
			SEQUENCE { 
				arrayDiskEnclosureConnectionNumber
					INTEGER,
				arrayDiskEnclosureConnectionArrayDiskName
					DisplayString,
				arrayDiskEnclosureConnectionArrayDiskNumber
					INTEGER,
				arrayDiskEnclosureConnectionEnclosureName
					DisplayString,
				arrayDiskEnclosureConnectionEnclosureNumber
					INTEGER,
				arrayDiskEnclosureConnectionControllerName
					DisplayString,
				arrayDiskEnclosureConnectionControllerNumber
					INTEGER
			 }

		-- 1.3.6.1.4.1.674.10893.1.20.130.5.1.1
		arrayDiskEnclosureConnectionNumber OBJECT-TYPE
			SYNTAX INTEGER (1..1000000000)
			ACCESS read-only
			STATUS mandatory
			DESCRIPTION
				"Instance number of this array disk connection entry.
				This table shows the array disk to enclosure relationship."
			::= { arrayDiskEnclosureConnectionEntry 1 }

		
		-- 1.3.6.1.4.1.674.10893.1.20.130.5.1.2
		arrayDiskEnclosureConnectionArrayDiskName OBJECT-TYPE
			SYNTAX DisplayString
			ACCESS read-only
			STATUS mandatory
			DESCRIPTION
				"The name of the array disk in this connection as represented in Storage Management."
			::= { arrayDiskEnclosureConnectionEntry 2 }

		
		-- 1.3.6.1.4.1.674.10893.1.20.130.5.1.3
		arrayDiskEnclosureConnectionArrayDiskNumber OBJECT-TYPE
			SYNTAX INTEGER
			ACCESS read-only
			STATUS mandatory
			DESCRIPTION
				"The instance number of the array disk in the arrayDiskTable
				in this connection."
			::= { arrayDiskEnclosureConnectionEntry 3 }

		
		-- 1.3.6.1.4.1.674.10893.1.20.130.5.1.4
		arrayDiskEnclosureConnectionEnclosureName OBJECT-TYPE
			SYNTAX DisplayString
			ACCESS read-only
			STATUS mandatory
			DESCRIPTION
				"The name of the enclosure as represented in Storage Management
				to which this array disk belongs.
				"
			::= { arrayDiskEnclosureConnectionEntry 4 }

		
		-- 1.3.6.1.4.1.674.10893.1.20.130.5.1.5
		arrayDiskEnclosureConnectionEnclosureNumber OBJECT-TYPE
			SYNTAX INTEGER
			ACCESS read-only
			STATUS mandatory
			DESCRIPTION
				"The instance number in the enclosureTable of the enclosure 
				to which this array disk belongs."
			::= { arrayDiskEnclosureConnectionEntry 5 }

		
		-- 1.3.6.1.4.1.674.10893.1.20.130.5.1.6
		arrayDiskEnclosureConnectionControllerName OBJECT-TYPE
			SYNTAX DisplayString
			ACCESS read-only
			STATUS mandatory
			DESCRIPTION
				"The name of the controller as represented in Storage Management
				to which this array disk is connected."
			::= { arrayDiskEnclosureConnectionEntry 6 }

		
		-- 1.3.6.1.4.1.674.10893.1.20.130.5.1.7
		arrayDiskEnclosureConnectionControllerNumber OBJECT-TYPE
			SYNTAX INTEGER
			ACCESS read-only
			STATUS mandatory
			DESCRIPTION
				"The instance number in the controllerTable of the controller 
				to which this array disk is connected."
			::= { arrayDiskEnclosureConnectionEntry 7 }

		
		-- 1.3.6.1.4.1.674.10893.1.20.130.6
		arrayDiskChannelConnectionTable OBJECT-TYPE
			SYNTAX SEQUENCE OF ArrayDiskChannelConnectionEntry
			ACCESS not-accessible
			STATUS mandatory
			DESCRIPTION
				"A table of the connections between array disks, their channel, and 
				their associated controller.  For each object in the table, its 
				object number corresponds to an instance number in the appropriate 
				MIB table for that object where all of the object properties can be 
				found.
				Note: Only array disks that are NOT part of an enclosure will be 
				listed in this table.  Backplanes are considered enclosures by
				Storage Management."
			::= { physicalDevices 6 }

		
		-- 1.3.6.1.4.1.674.10893.1.20.130.6.1
		arrayDiskChannelConnectionEntry OBJECT-TYPE
			SYNTAX ArrayDiskChannelConnectionEntry
			ACCESS not-accessible
			STATUS mandatory
			DESCRIPTION
				"An entry in the Array Disk Channel Connection table . A row in this table cannot be
				created or deleted by SNMP operations on columns of the table."
			INDEX { arrayDiskChannelConnectionNumber }
			::= { arrayDiskChannelConnectionTable 1 }

		
		ArrayDiskChannelConnectionEntry ::=
			SEQUENCE { 
				arrayDiskChannelConnectionNumber
					INTEGER,
				arrayDiskChannelConnectionArrayDiskName
					DisplayString,
				arrayDiskChannelConnectionArrayDiskNumber
					INTEGER,
				arrayDiskChannelConnectionChannelName
					DisplayString,
				arrayDiskChannelConnectionChannelNumber
					INTEGER,
				arrayDiskChannelConnectionControllerName
					DisplayString,
				arrayDiskChannelConnectionControllerNumber
					INTEGER
			 }

		-- 1.3.6.1.4.1.674.10893.1.20.130.6.1.1
		arrayDiskChannelConnectionNumber OBJECT-TYPE
			SYNTAX INTEGER (1..1000000000)
			ACCESS read-only
			STATUS mandatory
			DESCRIPTION
				"Instance number of this array disk connection entry.
				This table shows the array disk to SCSI channel relationship.
				There is no enclosure service processor associated with these
				array disks."
			::= { arrayDiskChannelConnectionEntry 1 }

		
		-- 1.3.6.1.4.1.674.10893.1.20.130.6.1.2
		arrayDiskChannelConnectionArrayDiskName OBJECT-TYPE
			SYNTAX DisplayString
			ACCESS read-only
			STATUS mandatory
			DESCRIPTION
				"The name of the array disk in this connection
				as represented in Storage Management."
			::= { arrayDiskChannelConnectionEntry 2 }

		
		-- 1.3.6.1.4.1.674.10893.1.20.130.6.1.3
		arrayDiskChannelConnectionArrayDiskNumber OBJECT-TYPE
			SYNTAX INTEGER
			ACCESS read-only
			STATUS mandatory
			DESCRIPTION
				"The instance number of the array disk in the arrayDiskTable
				in this connection."
			::= { arrayDiskChannelConnectionEntry 3 }

		
		-- 1.3.6.1.4.1.674.10893.1.20.130.6.1.4
		arrayDiskChannelConnectionChannelName OBJECT-TYPE
			SYNTAX DisplayString
			ACCESS read-only
			STATUS mandatory
			DESCRIPTION
				"The name of the channel as represented in Storage Management
				to which is array disk is connected."
			::= { arrayDiskChannelConnectionEntry 4 }

		
		-- 1.3.6.1.4.1.674.10893.1.20.130.6.1.5
		arrayDiskChannelConnectionChannelNumber OBJECT-TYPE
			SYNTAX INTEGER
			ACCESS read-only
			STATUS mandatory
			DESCRIPTION
				"The instance number of the channel in the channelTable to 
				which this array disk is connected."
			::= { arrayDiskChannelConnectionEntry 5 }

		
		-- 1.3.6.1.4.1.674.10893.1.20.130.6.1.6
		arrayDiskChannelConnectionControllerName OBJECT-TYPE
			SYNTAX DisplayString
			ACCESS read-only
			STATUS mandatory
			DESCRIPTION
				"The name of the controller as represented in Storage Management
				to which this array disk is connected."
			::= { arrayDiskChannelConnectionEntry 6 }

		
		-- 1.3.6.1.4.1.674.10893.1.20.130.6.1.7
		arrayDiskChannelConnectionControllerNumber OBJECT-TYPE
			SYNTAX INTEGER
			ACCESS read-only
			STATUS mandatory
			DESCRIPTION
				"The instance number in the controllerTable of the controller 
				to which this array disk is connected."
			::= { arrayDiskChannelConnectionEntry 7 }

		
		-- 1.3.6.1.4.1.674.10893.1.20.130.7
		fanTable OBJECT-TYPE
			SYNTAX SEQUENCE OF FanEntry
			ACCESS not-accessible
			STATUS mandatory
			DESCRIPTION
				"A table of managed Fans. The number of entries is 
				related to number of Fans discovered in the system.
				The maximum number of entries is implementation dependent.
				Note: The properties in this table may not be applicable to all entries."
			::= { physicalDevices 7 }

		
		-- 1.3.6.1.4.1.674.10893.1.20.130.7.1
		fanEntry OBJECT-TYPE
			SYNTAX FanEntry
			ACCESS not-accessible
			STATUS mandatory
			DESCRIPTION
				"An entry in the Fan table . A row in this table cannot be
				created or deleted by SNMP operations on columns of the table."
			INDEX { fanNumber }
			::= { fanTable 1 }

		
		FanEntry ::=
			SEQUENCE { 
				fanNumber
					INTEGER,
				fanName
					DisplayString,
				fanVendor
					DisplayString,
				fanState
					INTEGER,
				fanSeverity
					INTEGER,
				fanProbeUnit
					DisplayString,
				fanProbeMinWarning
					DisplayString,
				fanProbeMinCritical
					DisplayString,
				fanProbeMaxWarning
					DisplayString,
				fanProbeMaxCritical
					DisplayString,
				fanProbeCurrValue
					DisplayString,
				fan1PartNumber
					DisplayString,
				fan2PartNumber
					DisplayString,
				fanRollUpStatus
					DellStatus,
				fanComponentStatus
					DellStatus,
				fanNexusID
					DisplayString,
				fanRevision
					DisplayString
			 }

		-- 1.3.6.1.4.1.674.10893.1.20.130.7.1.1
		fanNumber OBJECT-TYPE
			SYNTAX INTEGER (1..1000000000)
			ACCESS read-only
			STATUS mandatory
			DESCRIPTION
				"Instance number of this fan entry."
			::= { fanEntry 1 }

		
		-- 1.3.6.1.4.1.674.10893.1.20.130.7.1.2
		fanName OBJECT-TYPE
			SYNTAX DisplayString
			ACCESS read-only
			STATUS mandatory
			DESCRIPTION
				"The fan's name as represented in Storage Management."
			::= { fanEntry 2 }

		
		-- 1.3.6.1.4.1.674.10893.1.20.130.7.1.3
		fanVendor OBJECT-TYPE
			SYNTAX DisplayString
			ACCESS read-only
			STATUS mandatory
			DESCRIPTION
				"The fan's (re)seller's name."
			::= { fanEntry 3 }

		
		-- 1.3.6.1.4.1.674.10893.1.20.130.7.1.4
		fanState OBJECT-TYPE
			SYNTAX INTEGER
				{
				ready(1),
				failed(2),
				degraded(6),
				removed(11),
				missing(21)
				}
			ACCESS read-only
			STATUS mandatory
			DESCRIPTION
				"The current condition of the fan.
				Possible states:
				0:  Unknown
				1:  Ready
				2:  Failed
				3:  Online
				4:  Offline
				6:  Degraded
				21: Missing"
			::= { fanEntry 4 }

		
		-- 1.3.6.1.4.1.674.10893.1.20.130.7.1.5
		fanSeverity OBJECT-TYPE
			SYNTAX INTEGER
				{
				warning(1),
				error(2),
				failure(3)
				}
			ACCESS read-only
			STATUS obsolete
			DESCRIPTION
				"This entry is obsolete for Storage Management.
				It was replaced with RollUpStatus and ComponentStatus for each device."
			::= { fanEntry 5 }

		
		-- 1.3.6.1.4.1.674.10893.1.20.130.7.1.6
		fanProbeUnit OBJECT-TYPE
			SYNTAX DisplayString
			ACCESS read-only
			STATUS obsolete
			DESCRIPTION
				"This entry is obsolete for Storage Management."
			::= { fanEntry 6 }

		
		-- 1.3.6.1.4.1.674.10893.1.20.130.7.1.7
		fanProbeMinWarning OBJECT-TYPE
			SYNTAX DisplayString
			ACCESS read-only
			STATUS obsolete
			DESCRIPTION
				"This entry is obsolete.  This setting is not supported
				by fans managed under Storage Management."
			::= { fanEntry 7 }

		
		-- 1.3.6.1.4.1.674.10893.1.20.130.7.1.8
		fanProbeMinCritical OBJECT-TYPE
			SYNTAX DisplayString
			ACCESS read-only
			STATUS obsolete
			DESCRIPTION
				"This entry is obsolete.  This setting is not supported
				by fans managed under Storage Management."
			::= { fanEntry 8 }

		
		-- 1.3.6.1.4.1.674.10893.1.20.130.7.1.9
		fanProbeMaxWarning OBJECT-TYPE
			SYNTAX DisplayString
			ACCESS read-only
			STATUS obsolete
			DESCRIPTION
				"This entry is obsolete.  This setting is not supported
				by fans managed under Storage Management."
			::= { fanEntry 9 }

		
		-- 1.3.6.1.4.1.674.10893.1.20.130.7.1.10
		fanProbeMaxCritical OBJECT-TYPE
			SYNTAX DisplayString
			ACCESS read-only
			STATUS obsolete
			DESCRIPTION
				"This entry is obsolete.  This setting is not supported
				by fans managed under Storage Management."
			::= { fanEntry 10 }

		
		-- 1.3.6.1.4.1.674.10893.1.20.130.7.1.11
		fanProbeCurrValue OBJECT-TYPE
			SYNTAX DisplayString
			ACCESS read-only
			STATUS mandatory
			DESCRIPTION
				"The current speed of the fan.
				"
			::= { fanEntry 11 }

		
		-- 1.3.6.1.4.1.674.10893.1.20.130.7.1.12
		fan1PartNumber OBJECT-TYPE
			SYNTAX DisplayString
			ACCESS read-only
			STATUS mandatory
			DESCRIPTION
				"The part number of the fan in the enclosure."
			::= { fanEntry 12 }

		
		-- 1.3.6.1.4.1.674.10893.1.20.130.7.1.13
		fan2PartNumber OBJECT-TYPE
			SYNTAX DisplayString
			ACCESS read-only
			STATUS obsolete
			DESCRIPTION
				"This entry is obsolete.  This setting is not supported
				by fans managed under Storage Management."
			::= { fanEntry 13 }

		
		-- 1.3.6.1.4.1.674.10893.1.20.130.7.1.14
		fanRollUpStatus OBJECT-TYPE
			SYNTAX DellStatus
			ACCESS read-only
			STATUS mandatory
			DESCRIPTION
				"Severity of the fan state.
				This is the combined status of the fan and its components.
				Possible values:
				1: Other
				2: Unknown
				3: OK 
				4: Non-critical 
				5: Critical
				6: Non-recoverable"
			::= { fanEntry 14 }

		
		-- 1.3.6.1.4.1.674.10893.1.20.130.7.1.15
		fanComponentStatus OBJECT-TYPE
			SYNTAX DellStatus
			ACCESS read-only
			STATUS mandatory
			DESCRIPTION
				"The status of the fan itself without the 
				propagation of any contained component status.
				Possible values:
				1: Other
				2: Unknown
				3: OK 
				4: Non-critical 
				5: Critical
				6: Non-recoverable"
			::= { fanEntry 15 }

		
		-- 1.3.6.1.4.1.674.10893.1.20.130.7.1.16
		fanNexusID OBJECT-TYPE
			SYNTAX DisplayString
			ACCESS read-only
			STATUS mandatory
			DESCRIPTION
				"Durable unique ID for this fan."
			::= { fanEntry 16 }

		
		-- 1.3.6.1.4.1.674.10893.1.20.130.7.1.17
		fanRevision OBJECT-TYPE
			SYNTAX DisplayString
			ACCESS read-only
			STATUS mandatory
			DESCRIPTION
				"The revision number of the fan in the enclosure."
			::= { fanEntry 17 }

		
		-- 1.3.6.1.4.1.674.10893.1.20.130.8
		fanConnectionTable OBJECT-TYPE
			SYNTAX SEQUENCE OF FanConnectionEntry
			ACCESS not-accessible
			STATUS mandatory
			DESCRIPTION
				"A table of the connections between each fan on 
				the managed node and its enclosure.  Each enclosure 
				number in the table corresponds to that enclosure instance
				in the Enclosure Table."
			::= { physicalDevices 8 }

		
		-- 1.3.6.1.4.1.674.10893.1.20.130.8.1
		fanConnectionEntry OBJECT-TYPE
			SYNTAX FanConnectionEntry
			ACCESS not-accessible
			STATUS mandatory
			DESCRIPTION
				"An entry in the Fan Connection table . A row in this table cannot be
				created or deleted by SNMP operations on columns of the table."
			INDEX { fanConnectionNumber }
			::= { fanConnectionTable 1 }

		
		FanConnectionEntry ::=
			SEQUENCE { 
				fanConnectionNumber
					INTEGER,
				fanConnectionFanName
					DisplayString,
				fanConnectionFanNumber
					INTEGER,
				fanConnectionEnclosureName
					DisplayString,
				fanConnectionEnclosureNumber
					INTEGER
			 }

		-- 1.3.6.1.4.1.674.10893.1.20.130.8.1.1
		fanConnectionNumber OBJECT-TYPE
			SYNTAX INTEGER (1..255)
			ACCESS read-only
			STATUS mandatory
			DESCRIPTION
				"Instance number of this fan connection entry."
			::= { fanConnectionEntry 1 }

		
		-- 1.3.6.1.4.1.674.10893.1.20.130.8.1.2
		fanConnectionFanName OBJECT-TYPE
			SYNTAX DisplayString
			ACCESS read-only
			STATUS mandatory
			DESCRIPTION
				"The name of the fan in this connection as represented in Storage Management."
			::= { fanConnectionEntry 2 }

		
		-- 1.3.6.1.4.1.674.10893.1.20.130.8.1.3
		fanConnectionFanNumber OBJECT-TYPE
			SYNTAX INTEGER
			ACCESS read-only
			STATUS mandatory
			DESCRIPTION
				"The instance number of the fan in the fanTable in this connection."
			::= { fanConnectionEntry 3 }

		
		-- 1.3.6.1.4.1.674.10893.1.20.130.8.1.4
		fanConnectionEnclosureName OBJECT-TYPE
			SYNTAX DisplayString
			ACCESS read-only
			STATUS mandatory
			DESCRIPTION
				"The name of the enclosure as represented in Storage Management
				to which this fan belongs."
			::= { fanConnectionEntry 4 }

		
		-- 1.3.6.1.4.1.674.10893.1.20.130.8.1.5
		fanConnectionEnclosureNumber OBJECT-TYPE
			SYNTAX INTEGER
			ACCESS read-only
			STATUS mandatory
			DESCRIPTION
				"The instance number of the enclosure in the enclosureTable
				to which this fan belongs."
			::= { fanConnectionEntry 5 }

		
		-- 1.3.6.1.4.1.674.10893.1.20.130.9
		powerSupplyTable OBJECT-TYPE
			SYNTAX SEQUENCE OF PowerSupplyEntry
			ACCESS not-accessible
			STATUS mandatory
			DESCRIPTION
				"A table of managed Power Supplies. The number of entries is 
				related to number of Power Supplies discovered in the system.
				The maximum number of entries is implementation dependent.
				Note: The properties in this table may not be applicable to all entries."
			::= { physicalDevices 9 }

		
		-- 1.3.6.1.4.1.674.10893.1.20.130.9.1
		powerSupplyEntry OBJECT-TYPE
			SYNTAX PowerSupplyEntry
			ACCESS not-accessible
			STATUS mandatory
			DESCRIPTION
				"An entry in the Power Supply table . A row in this table cannot be
				created or deleted by SNMP operations on columns of the table."
			INDEX { powerSupplyNumber }
			::= { powerSupplyTable 1 }

		
		PowerSupplyEntry ::=
			SEQUENCE { 
				powerSupplyNumber
					INTEGER,
				powerSupplyName
					DisplayString,
				powerSupplyVendor
					DisplayString,
				powerSupplyState
					INTEGER,
				powerSupplySeverity
					INTEGER,
				powerSupply1PartNumber
					DisplayString,
				powerSupply2PartNumber
					DisplayString,
				powerSupplyRollUpStatus
					DellStatus,
				powerSupplyComponentStatus
					DellStatus,
				powerSupplyNexusID
					DisplayString,
				powerSupplyRevision
					DisplayString
			 }

		-- 1.3.6.1.4.1.674.10893.1.20.130.9.1.1
		powerSupplyNumber OBJECT-TYPE
			SYNTAX INTEGER (1..255)
			ACCESS read-only
			STATUS mandatory
			DESCRIPTION
				"Instance number of this power supply entry."
			::= { powerSupplyEntry 1 }

		
		-- 1.3.6.1.4.1.674.10893.1.20.130.9.1.2
		powerSupplyName OBJECT-TYPE
			SYNTAX DisplayString
			ACCESS read-only
			STATUS mandatory
			DESCRIPTION
				"The power supply's name as represented in Storage Management."
			::= { powerSupplyEntry 2 }

		
		-- 1.3.6.1.4.1.674.10893.1.20.130.9.1.3
		powerSupplyVendor OBJECT-TYPE
			SYNTAX DisplayString
			ACCESS read-only
			STATUS mandatory
			DESCRIPTION
				"The power supply's (re)seller's name."
			::= { powerSupplyEntry 3 }

		
		-- 1.3.6.1.4.1.674.10893.1.20.130.9.1.4
		powerSupplyState OBJECT-TYPE
			SYNTAX INTEGER
				{
				ready(1),
				failed(2),
				notInstalled(5),
				degraded(6),
				removed(11),
				missing(21)
				}
			ACCESS read-only
			STATUS mandatory
			DESCRIPTION
				"The current condition of the power supply.
				Possible states:
				0 : Unknown
				1 : Ready
				2 : Failed
				5 : Not Installed
				6 : Degraded
				11: Removed
				21: Missing"
			::= { powerSupplyEntry 4 }

		
		-- 1.3.6.1.4.1.674.10893.1.20.130.9.1.5
		powerSupplySeverity OBJECT-TYPE
			SYNTAX INTEGER
				{
				warning(1),
				error(2),
				failure(3)
				}
			ACCESS read-only
			STATUS obsolete
			DESCRIPTION
				"This entry is obsolete for Storage Management.
				It was replaced with RollUpStatus and ComponentStatus for each device."
			::= { powerSupplyEntry 5 }

		
		-- 1.3.6.1.4.1.674.10893.1.20.130.9.1.6
		powerSupply1PartNumber OBJECT-TYPE
			SYNTAX DisplayString
			ACCESS read-only
			STATUS mandatory
			DESCRIPTION
				"The part number of the power supply of the enclosure."
			::= { powerSupplyEntry 6 }

		
		-- 1.3.6.1.4.1.674.10893.1.20.130.9.1.7
		powerSupply2PartNumber OBJECT-TYPE
			SYNTAX DisplayString
			ACCESS read-only
			STATUS obsolete
			DESCRIPTION
				"This entry is obsolete. This setting is not supported
				by power supplies managed under Storage Management."
			::= { powerSupplyEntry 7 }

		
		-- 1.3.6.1.4.1.674.10893.1.20.130.9.1.8
		powerSupplyRollUpStatus OBJECT-TYPE
			SYNTAX DellStatus
			ACCESS read-only
			STATUS mandatory
			DESCRIPTION
				"Severity of the power supply state.
				This is the combined status of the power supply and its 
				components.
				Possible values:
				1: Other
				2: Unknown
				3: OK 
				4: Non-critical 
				5: Critical
				6: Non-recoverable"
			::= { powerSupplyEntry 8 }

		
		-- 1.3.6.1.4.1.674.10893.1.20.130.9.1.9
		powerSupplyComponentStatus OBJECT-TYPE
			SYNTAX DellStatus
			ACCESS read-only
			STATUS mandatory
			DESCRIPTION
				"The status of the power supply itself without the 
				propegation of any contained component status.
				Possible values:
				1: Other
				2: Unknown
				3: OK 
				4: Non-critical 
				5: Critical
				6: Non-recoverable"
			::= { powerSupplyEntry 9 }

		
		-- 1.3.6.1.4.1.674.10893.1.20.130.9.1.10
		powerSupplyNexusID OBJECT-TYPE
			SYNTAX DisplayString
			ACCESS read-only
			STATUS mandatory
			DESCRIPTION
				"Durable unique ID for this power supply."
			::= { powerSupplyEntry 10 }

		
		-- 1.3.6.1.4.1.674.10893.1.20.130.9.1.11
		powerSupplyRevision OBJECT-TYPE
			SYNTAX DisplayString
			ACCESS read-only
			STATUS mandatory
			DESCRIPTION
				"The revision number of the power supply in the enclosure."
			::= { powerSupplyEntry 11 }

		
		-- 1.3.6.1.4.1.674.10893.1.20.130.10
		powerSupplyConnectionTable OBJECT-TYPE
			SYNTAX SEQUENCE OF PowerSupplyConnectionEntry
			ACCESS not-accessible
			STATUS mandatory
			DESCRIPTION
				"A table of the connections between each power 
				supply on the managed node and its enclosure.  Each
				enclosure number in the table corresponds to that 
				enclosure instance in the Enclosure Table."
			::= { physicalDevices 10 }

		
		-- 1.3.6.1.4.1.674.10893.1.20.130.10.1
		powerSupplyConnectionEntry OBJECT-TYPE
			SYNTAX PowerSupplyConnectionEntry
			ACCESS not-accessible
			STATUS mandatory
			DESCRIPTION
				"An entry in the Power Supply Connection table . A row in this table cannot be
				created or deleted by SNMP operations on columns of the table."
			INDEX { powerSupplyConnectionNumber }
			::= { powerSupplyConnectionTable 1 }

		
		PowerSupplyConnectionEntry ::=
			SEQUENCE { 
				powerSupplyConnectionNumber
					INTEGER,
				powerSupplyConnectionPowersupplyName
					DisplayString,
				powerSupplyConnectionPowersupplyNumber
					INTEGER,
				powerSupplyConnectionEnclosureName
					DisplayString,
				powerSupplyConnectionEnclosureNumber
					INTEGER
			 }

		-- 1.3.6.1.4.1.674.10893.1.20.130.10.1.1
		powerSupplyConnectionNumber OBJECT-TYPE
			SYNTAX INTEGER (1..255)
			ACCESS read-only
			STATUS mandatory
			DESCRIPTION
				"Instance number of this power supply connection entry."
			::= { powerSupplyConnectionEntry 1 }

		
		-- 1.3.6.1.4.1.674.10893.1.20.130.10.1.2
		powerSupplyConnectionPowersupplyName OBJECT-TYPE
			SYNTAX DisplayString
			ACCESS read-only
			STATUS mandatory
			DESCRIPTION
				"The name of the power supply in this connection 
				as represented in Storage Management."
			::= { powerSupplyConnectionEntry 2 }

		
		-- 1.3.6.1.4.1.674.10893.1.20.130.10.1.3
		powerSupplyConnectionPowersupplyNumber OBJECT-TYPE
			SYNTAX INTEGER
			ACCESS read-only
			STATUS mandatory
			DESCRIPTION
				"This instance number in the powersupplyTable
				of the power supply in this connection."
			::= { powerSupplyConnectionEntry 3 }

		
		-- 1.3.6.1.4.1.674.10893.1.20.130.10.1.4
		powerSupplyConnectionEnclosureName OBJECT-TYPE
			SYNTAX DisplayString
			ACCESS read-only
			STATUS mandatory
			DESCRIPTION
				"The name of the enclosure to which this power supply is
				connected as represented in Storage Management."
			::= { powerSupplyConnectionEntry 4 }

		
		-- 1.3.6.1.4.1.674.10893.1.20.130.10.1.5
		powerSupplyConnectionEnclosureNumber OBJECT-TYPE
			SYNTAX INTEGER
			ACCESS read-only
			STATUS mandatory
			DESCRIPTION
				"The instance number of the enclosure in the enclosureTable
				to which this power supply is connected."
			::= { powerSupplyConnectionEntry 5 }

		
		-- 1.3.6.1.4.1.674.10893.1.20.130.11
		temperatureProbeTable OBJECT-TYPE
			SYNTAX SEQUENCE OF TemperatureProbeEntry
			ACCESS not-accessible
			STATUS mandatory
			DESCRIPTION
				"A table of managed Temperature Probes. The number of entries is 
				related to number of Temperature Probes discovered in the system.
				The maximum number of entries is implementation dependent.
				Note: The properties in this table may not be applicable to all entries."
			::= { physicalDevices 11 }

		
		-- 1.3.6.1.4.1.674.10893.1.20.130.11.1
		temperatureProbeEntry OBJECT-TYPE
			SYNTAX TemperatureProbeEntry
			ACCESS not-accessible
			STATUS mandatory
			DESCRIPTION
				"An entry in the Temperature Probe table . A row in this table cannot be
				created or deleted by SNMP operations on columns of the table."
			INDEX { temperatureProbeNumber }
			::= { temperatureProbeTable 1 }

		
		TemperatureProbeEntry ::=
			SEQUENCE { 
				temperatureProbeNumber
					INTEGER,
				temperatureProbeName
					DisplayString,
				temperatureProbeVendor
					DisplayString,
				temperatureProbeState
					INTEGER,
				temperatureProbeSeverity
					INTEGER,
				temperatureProbeUnit
					DisplayString,
				temperatureProbeMinWarning
					INTEGER,
				temperatureProbeMinCritical
					INTEGER,
				temperatureProbeMaxWarning
					INTEGER,
				temperatureProbeMaxCritical
					INTEGER,
				temperatureProbeCurValue
					INTEGER,
				temperatureProbeRollUpStatus
					DellStatus,
				temperatureProbeComponentStatus
					DellStatus,
				temperatureProbeNexusID
					DisplayString
			 }

		-- 1.3.6.1.4.1.674.10893.1.20.130.11.1.1
		temperatureProbeNumber OBJECT-TYPE
			SYNTAX INTEGER (1..255)
			ACCESS read-only
			STATUS mandatory
			DESCRIPTION
				"Instance number of this temperature probe entry."
			::= { temperatureProbeEntry 1 }

		
		-- 1.3.6.1.4.1.674.10893.1.20.130.11.1.2
		temperatureProbeName OBJECT-TYPE
			SYNTAX DisplayString
			ACCESS read-only
			STATUS mandatory
			DESCRIPTION
				"Name of this temperature probe as represented in Storage Management."
			::= { temperatureProbeEntry 2 }

		
		-- 1.3.6.1.4.1.674.10893.1.20.130.11.1.3
		temperatureProbeVendor OBJECT-TYPE
			SYNTAX DisplayString
			ACCESS read-only
			STATUS mandatory
			DESCRIPTION
				"Temperature probe's (re)seller's name."
			::= { temperatureProbeEntry 3 }

		
		-- 1.3.6.1.4.1.674.10893.1.20.130.11.1.4
		temperatureProbeState OBJECT-TYPE
			SYNTAX INTEGER
				{
				ready(1),
				failed(2),
				offline(4),
				degraded(6),
				inactive(9),
				missing(21)
				}
			ACCESS read-only
			STATUS mandatory
			DESCRIPTION
				"The current condition of the temperature probe.
				Possible states:
				0:  Unknown
				1:  Ready
				2:  Failed (Minimum Failure Threshold Exceeded, 
				           Maximum Failure Threshold Exceeded)
				4:  Offline
				6:  Degraded (Minimum Warning Threshold Exceeded,
				             Maximum Warning Threshold Exceeded)
				9:  Inactive
				21: Missing"
			::= { temperatureProbeEntry 4 }

		
		-- 1.3.6.1.4.1.674.10893.1.20.130.11.1.5
		temperatureProbeSeverity OBJECT-TYPE
			SYNTAX INTEGER
				{
				warning(1),
				error(2),
				failure(3)
				}
			ACCESS read-only
			STATUS obsolete
			DESCRIPTION
				"This entry is obsolete for Storage Management.
				It was replaced with RollUpStatus and ComponentStatus for each device."
			::= { temperatureProbeEntry 5 }

		
		-- 1.3.6.1.4.1.674.10893.1.20.130.11.1.6
		temperatureProbeUnit OBJECT-TYPE
			SYNTAX DisplayString
			ACCESS read-only
			STATUS mandatory
			DESCRIPTION
				"The units that will be used to display temperatures for this 
				temperature probe."
			::= { temperatureProbeEntry 6 }

		
		-- 1.3.6.1.4.1.674.10893.1.20.130.11.1.7
		temperatureProbeMinWarning OBJECT-TYPE
			SYNTAX INTEGER
			ACCESS read-only
			STATUS mandatory
			DESCRIPTION
				"The minimum temperature that will force the probe into
				a warning state."
			::= { temperatureProbeEntry 7 }

		
		-- 1.3.6.1.4.1.674.10893.1.20.130.11.1.8
		temperatureProbeMinCritical OBJECT-TYPE
			SYNTAX INTEGER
			ACCESS read-only
			STATUS mandatory
			DESCRIPTION
				"The minimum temperature that will force the probe into
				an error state."
			::= { temperatureProbeEntry 8 }

		
		-- 1.3.6.1.4.1.674.10893.1.20.130.11.1.9
		temperatureProbeMaxWarning OBJECT-TYPE
			SYNTAX INTEGER
			ACCESS read-only
			STATUS mandatory
			DESCRIPTION
				"The maximum temperature that will force the probe into
				a warning state."
			::= { temperatureProbeEntry 9 }

		
		-- 1.3.6.1.4.1.674.10893.1.20.130.11.1.10
		temperatureProbeMaxCritical OBJECT-TYPE
			SYNTAX INTEGER
			ACCESS read-only
			STATUS mandatory
			DESCRIPTION
				"The maximum temperature that will force the probe into
				an error state."
			::= { temperatureProbeEntry 10 }

		
		-- 1.3.6.1.4.1.674.10893.1.20.130.11.1.11
		temperatureProbeCurValue OBJECT-TYPE
			SYNTAX INTEGER
			ACCESS read-only
			STATUS mandatory
			DESCRIPTION
				"The current temperature of this probe."
			::= { temperatureProbeEntry 11 }

		
		-- 1.3.6.1.4.1.674.10893.1.20.130.11.1.12
		temperatureProbeRollUpStatus OBJECT-TYPE
			SYNTAX DellStatus
			ACCESS read-only
			STATUS mandatory
			DESCRIPTION
				"Severity of the temperature probe state.
				This is the combined status of the temperature probe
				and its components.
				Possible values:
				1: Other
				2: Unknown
				3: OK 
				4: Non-critical 
				5: Critical
				6: Non-recoverable"
			::= { temperatureProbeEntry 12 }

		
		-- 1.3.6.1.4.1.674.10893.1.20.130.11.1.13
		temperatureProbeComponentStatus OBJECT-TYPE
			SYNTAX DellStatus
			ACCESS read-only
			STATUS mandatory
			DESCRIPTION
				"The status of the temperature probe itself without the propagation
				of any contained component status.
				Possible values:
				1: Other
				2: Unknown
				3: OK 
				4: Non-critical 
				5: Critical
				6: Non-recoverable"
			::= { temperatureProbeEntry 13 }

		
		-- 1.3.6.1.4.1.674.10893.1.20.130.11.1.14
		temperatureProbeNexusID OBJECT-TYPE
			SYNTAX DisplayString
			ACCESS read-only
			STATUS mandatory
			DESCRIPTION
				"Durable unique ID for this temperature probe."
			::= { temperatureProbeEntry 14 }

		
		-- 1.3.6.1.4.1.674.10893.1.20.130.12
		temperatureConnectionTable OBJECT-TYPE
			SYNTAX SEQUENCE OF TemperatureConnectionEntry
			ACCESS not-accessible
			STATUS mandatory
			DESCRIPTION
				"A table of the connections between each 
				temperature probe on the managed node and its enclosure. 
				Each enclosure number in the table corresponds to that 
				enclosure instance in the Enclosure Table."
			::= { physicalDevices 12 }

		
		-- 1.3.6.1.4.1.674.10893.1.20.130.12.1
		temperatureConnectionEntry OBJECT-TYPE
			SYNTAX TemperatureConnectionEntry
			ACCESS not-accessible
			STATUS mandatory
			DESCRIPTION
				"An entry in the Temperature Probe Connection table . A row in this table cannot be
				created or deleted by SNMP operations on columns of the table."
			INDEX { temperatureConnectionNumber }
			::= { temperatureConnectionTable 1 }

		
		TemperatureConnectionEntry ::=
			SEQUENCE { 
				temperatureConnectionNumber
					INTEGER,
				temperatureConnectionTemperatureName
					DisplayString,
				temperatureConnectionTemperatureNumber
					INTEGER,
				temperatureConnectionEnclosureName
					DisplayString,
				temperatureConnectionEnclosureNumber
					INTEGER
			 }

		-- 1.3.6.1.4.1.674.10893.1.20.130.12.1.1
		temperatureConnectionNumber OBJECT-TYPE
			SYNTAX INTEGER (1..255)
			ACCESS read-only
			STATUS mandatory
			DESCRIPTION
				"Instance number of this temperature probe connection entry."
			::= { temperatureConnectionEntry 1 }

		
		-- 1.3.6.1.4.1.674.10893.1.20.130.12.1.2
		temperatureConnectionTemperatureName OBJECT-TYPE
			SYNTAX DisplayString
			ACCESS read-only
			STATUS mandatory
			DESCRIPTION
				"The name of the temperature probe in this connection as 
				represented in Storage Management."
			::= { temperatureConnectionEntry 2 }

		
		-- 1.3.6.1.4.1.674.10893.1.20.130.12.1.3
		temperatureConnectionTemperatureNumber OBJECT-TYPE
			SYNTAX INTEGER
			ACCESS read-only
			STATUS mandatory
			DESCRIPTION
				"The instance number in the temperatureTable of the temperature probe in this connection."
			::= { temperatureConnectionEntry 3 }

		
		-- 1.3.6.1.4.1.674.10893.1.20.130.12.1.4
		temperatureConnectionEnclosureName OBJECT-TYPE
			SYNTAX DisplayString
			ACCESS read-only
			STATUS mandatory
			DESCRIPTION
				"The name of the enclosure as represented in Storage Management
				to which this temperature probe belongs."
			::= { temperatureConnectionEntry 4 }

		
		-- 1.3.6.1.4.1.674.10893.1.20.130.12.1.5
		temperatureConnectionEnclosureNumber OBJECT-TYPE
			SYNTAX INTEGER
			ACCESS read-only
			STATUS mandatory
			DESCRIPTION
				"The instance number of the enclosure in the enclosureTable
				to which this temperature probe belongs.
				"
			::= { temperatureConnectionEntry 5 }

		
		-- 1.3.6.1.4.1.674.10893.1.20.130.13
		enclosureManagementModuleTable OBJECT-TYPE
			SYNTAX SEQUENCE OF EnclosureManagementModuleEntry
			ACCESS not-accessible
			STATUS mandatory
			DESCRIPTION
				"A table of managed Enclosure Management Modules. The number of 
				entries is related to number of Enclosure Management Modules
				discovered in the system.  The maximum number of entries 
				is implementation dependent.
				Note: The properties in this table may not be applicable to all entries."
			::= { physicalDevices 13 }

		
		-- 1.3.6.1.4.1.674.10893.1.20.130.13.1
		enclosureManagementModuleEntry OBJECT-TYPE
			SYNTAX EnclosureManagementModuleEntry
			ACCESS not-accessible
			STATUS mandatory
			DESCRIPTION
				"An entry in the Enclosure Management Module table . A row in this table cannot be
				created or deleted by SNMP operations on columns of the table."
			INDEX { enclosureManagementModuleNumber }
			::= { enclosureManagementModuleTable 1 }

		
		EnclosureManagementModuleEntry ::=
			SEQUENCE { 
				enclosureManagementModuleNumber
					INTEGER,
				enclosureManagementModuleName
					DisplayString,
				enclosureManagementModuleVendor
					DisplayString,
				enclosureManagementModuleState
					INTEGER,
				enclosureManagementModuleSeverity
					INTEGER,
				enclosureManagementModulePartNumber
					DisplayString,
				enclosureManagementModuleType
					INTEGER,
				enclosureManagementModuleFWVersion
					DisplayString,
				enclosureManagementModuleMaxSpeed
					DisplayString,
				enclosureManagementModuleRollUpStatus
					DellStatus,
				enclosureManagementModuleComponentStatus
					DellStatus,
				enclosureManagementModuleNexusID
					DisplayString,
				enclosureManagementModuleRevision
					DisplayString
			 }

		-- 1.3.6.1.4.1.674.10893.1.20.130.13.1.1
		enclosureManagementModuleNumber OBJECT-TYPE
			SYNTAX INTEGER (1..255)
			ACCESS read-only
			STATUS mandatory
			DESCRIPTION
				"Instance number of this enclosure memory module entry."
			::= { enclosureManagementModuleEntry 1 }

		
		-- 1.3.6.1.4.1.674.10893.1.20.130.13.1.2
		enclosureManagementModuleName OBJECT-TYPE
			SYNTAX DisplayString
			ACCESS read-only
			STATUS mandatory
			DESCRIPTION
				"Name of this enclosure memory module as represented in 
				Storage Management."
			::= { enclosureManagementModuleEntry 2 }

		
		-- 1.3.6.1.4.1.674.10893.1.20.130.13.1.3
		enclosureManagementModuleVendor OBJECT-TYPE
			SYNTAX DisplayString
			ACCESS read-only
			STATUS mandatory
			DESCRIPTION
				"The management module's (re)seller's name."
			::= { enclosureManagementModuleEntry 3 }

		
		-- 1.3.6.1.4.1.674.10893.1.20.130.13.1.4
		enclosureManagementModuleState OBJECT-TYPE
			SYNTAX INTEGER
				{
				ready(1),
				failed(2),
				online(3),
				offline(4),
				notInstalled(5),
				degraded(6),
				missing(21)
				}
			ACCESS read-only
			STATUS mandatory
			DESCRIPTION
				"The current condition of the enclosure management 
				module.
				Possible states:
				0:  Unknown
				1:  Ready
				2:  Failed
				3:  Online
				4:  Offline
				5:  Not Installed
				6:  Degraded
				21: Missing"
			::= { enclosureManagementModuleEntry 4 }

		
		-- 1.3.6.1.4.1.674.10893.1.20.130.13.1.5
		enclosureManagementModuleSeverity OBJECT-TYPE
			SYNTAX INTEGER
				{
				warning(1),
				error(2),
				failure(3)
				}
			ACCESS read-only
			STATUS obsolete
			DESCRIPTION
				"This entry is obsolete for Storage Management.
				It was replaced with RollUpStatus and ComponentStatus for each device."
			::= { enclosureManagementModuleEntry 5 }

		
		-- 1.3.6.1.4.1.674.10893.1.20.130.13.1.6
		enclosureManagementModulePartNumber OBJECT-TYPE
			SYNTAX DisplayString
			ACCESS read-only
			STATUS mandatory
			DESCRIPTION
				"The part number of the enclosure memory module."
			::= { enclosureManagementModuleEntry 6 }

		
		-- 1.3.6.1.4.1.674.10893.1.20.130.13.1.7
		enclosureManagementModuleType OBJECT-TYPE
			SYNTAX INTEGER
				{
				eMM(1),
				terminationCard(2)
				}
			ACCESS read-only
			STATUS mandatory
			DESCRIPTION
				"The type of the enclosure management module.
				Possible values:
				0: Unknown
				1: EMM
				2: Termination Card"
			::= { enclosureManagementModuleEntry 7 }

		
		-- 1.3.6.1.4.1.674.10893.1.20.130.13.1.8
		enclosureManagementModuleFWVersion OBJECT-TYPE
			SYNTAX DisplayString
			ACCESS read-only
			STATUS mandatory
			DESCRIPTION
				"Firmware version of the enclosure memory module."
			::= { enclosureManagementModuleEntry 8 }

		
		-- 1.3.6.1.4.1.674.10893.1.20.130.13.1.9
		enclosureManagementModuleMaxSpeed OBJECT-TYPE
			SYNTAX DisplayString
			ACCESS read-only
			STATUS mandatory
			DESCRIPTION
				"The maximum bus speed of the enclosure management module."
			::= { enclosureManagementModuleEntry 9 }

		
		-- 1.3.6.1.4.1.674.10893.1.20.130.13.1.10
		enclosureManagementModuleRollUpStatus OBJECT-TYPE
			SYNTAX DellStatus
			ACCESS read-only
			STATUS mandatory
			DESCRIPTION
				"Severity of the enclosure management module state.
				This is the combined status of the EMM and its components.
				Possible values:
				1: Other
				2: Unknown
				3: OK 
				4: Non-critical 
				5: Critical
				6: Non-recoverable"
			::= { enclosureManagementModuleEntry 10 }

		
		-- 1.3.6.1.4.1.674.10893.1.20.130.13.1.11
		enclosureManagementModuleComponentStatus OBJECT-TYPE
			SYNTAX DellStatus
			ACCESS read-only
			STATUS mandatory
			DESCRIPTION
				"The status of the enclosure management module itself 
				without the propagation of any contained component status.
				Possible values:
				1: Other
				2: Unknown
				3: OK 
				4: Non-critical 
				5: Critical
				6: Non-recoverable"
			::= { enclosureManagementModuleEntry 11 }

		
		-- 1.3.6.1.4.1.674.10893.1.20.130.13.1.12
		enclosureManagementModuleNexusID OBJECT-TYPE
			SYNTAX DisplayString
			ACCESS read-only
			STATUS mandatory
			DESCRIPTION
				"Durable unique ID for this EMM."
			::= { enclosureManagementModuleEntry 12 }

		
		-- 1.3.6.1.4.1.674.10893.1.20.130.13.1.13
		enclosureManagementModuleRevision OBJECT-TYPE
			SYNTAX DisplayString
			ACCESS read-only
			STATUS mandatory
			DESCRIPTION
				"The revision number of the enclosure management module."
			::= { enclosureManagementModuleEntry 13 }

		
		-- 1.3.6.1.4.1.674.10893.1.20.130.14
		enclosureManagementModuleConnectionTable OBJECT-TYPE
			SYNTAX SEQUENCE OF EnclosureManagementModuleConnectionEntry
			ACCESS not-accessible
			STATUS mandatory
			DESCRIPTION
				"A table of the connections between each enclosure management module 
				on the managed node and its enclosure.  Each enclosure 
				number in the table corresponds to that enclosure instance
				in the Enclosure Table."
			::= { physicalDevices 14 }

		
		-- 1.3.6.1.4.1.674.10893.1.20.130.14.1
		enclosureManagementModuleConnectionEntry OBJECT-TYPE
			SYNTAX EnclosureManagementModuleConnectionEntry
			ACCESS not-accessible
			STATUS mandatory
			DESCRIPTION
				"An entry in the Enclosure Management Module Connection table . A row in this 
				table cannot be created or deleted by SNMP operations on columns of the table."
			INDEX { enclosureManagementModuleConnectionNumber }
			::= { enclosureManagementModuleConnectionTable 1 }

		
		EnclosureManagementModuleConnectionEntry ::=
			SEQUENCE { 
				enclosureManagementModuleConnectionNumber
					INTEGER,
				enclosureManagementModuleConnectionEMMName
					DisplayString,
				enclosureManagementModuleConnectionEMMNumber
					INTEGER,
				enclosureManagementModuleConnectionEnclosureName
					DisplayString,
				enclosureManagementModuleConnectionEnclosureNumber
					INTEGER
			 }

		-- 1.3.6.1.4.1.674.10893.1.20.130.14.1.1
		enclosureManagementModuleConnectionNumber OBJECT-TYPE
			SYNTAX INTEGER (1..255)
			ACCESS read-only
			STATUS mandatory
			DESCRIPTION
				"Instance number of this enclosure management module
				connection entry."
			::= { enclosureManagementModuleConnectionEntry 1 }

		
		-- 1.3.6.1.4.1.674.10893.1.20.130.14.1.2
		enclosureManagementModuleConnectionEMMName OBJECT-TYPE
			SYNTAX DisplayString
			ACCESS read-only
			STATUS mandatory
			DESCRIPTION
				"The name of the enclosure management module in this 
				connection as represented in Storage Management."
			::= { enclosureManagementModuleConnectionEntry 2 }

		
		-- 1.3.6.1.4.1.674.10893.1.20.130.14.1.3
		enclosureManagementModuleConnectionEMMNumber OBJECT-TYPE
			SYNTAX INTEGER
			ACCESS read-only
			STATUS mandatory
			DESCRIPTION
				"The instance number of the enclosure management module in 
				the enclosureManagementModuleTable in this connection."
			::= { enclosureManagementModuleConnectionEntry 3 }

		
		-- 1.3.6.1.4.1.674.10893.1.20.130.14.1.4
		enclosureManagementModuleConnectionEnclosureName OBJECT-TYPE
			SYNTAX DisplayString
			ACCESS read-only
			STATUS mandatory
			DESCRIPTION
				"The name of the enclosure as represented in Storage Management
				to which this enclosure management module belongs."
			::= { enclosureManagementModuleConnectionEntry 4 }

		
		-- 1.3.6.1.4.1.674.10893.1.20.130.14.1.5
		enclosureManagementModuleConnectionEnclosureNumber OBJECT-TYPE
			SYNTAX INTEGER
			ACCESS read-only
			STATUS mandatory
			DESCRIPTION
				"The instance number of the enclosure in the enclosureTable
				to which this enclosure management module belongs."
			::= { enclosureManagementModuleConnectionEntry 5 }

		
		-- 1.3.6.1.4.1.674.10893.1.20.130.15
		batteryTable OBJECT-TYPE
			SYNTAX SEQUENCE OF BatteryEntry
			ACCESS not-accessible
			STATUS mandatory
			DESCRIPTION
				"A table of managed Batteries. The number of 
				entries is related to number of Batteries
				discovered in the system.  The maximum number of entries 
				is implementation dependent.
				Note: The properties in this table may not be applicable to all entries."
			::= { physicalDevices 15 }

		
		-- 1.3.6.1.4.1.674.10893.1.20.130.15.1
		batteryEntry OBJECT-TYPE
			SYNTAX BatteryEntry
			ACCESS not-accessible
			STATUS mandatory
			DESCRIPTION
				"An entry in the Battery table . A row in this table cannot be
				created or deleted by SNMP operations on columns of the table."
			INDEX { batteryNumber }
			::= { batteryTable 1 }

		
		BatteryEntry ::=
			SEQUENCE { 
				batteryNumber
					INTEGER,
				batteryName
					DisplayString,
				batteryVendor
					DisplayString,
				batteryState
					INTEGER,
				batteryRollUpStatus
					DellStatus,
				batteryComponentStatus
					DellStatus,
				batteryChargeCount
					INTEGER,
				batteryMaxChargeCount
					INTEGER,
				batteryNexusID
					DisplayString,
				batteryPredictedCapacity
					INTEGER,
				batteryNextLearnTime
					INTEGER,
				batteryLearnState
					INTEGER,
				batteryMaxLearnDelay
					INTEGER
			 }

		-- 1.3.6.1.4.1.674.10893.1.20.130.15.1.1
		batteryNumber OBJECT-TYPE
			SYNTAX INTEGER (1..255)
			ACCESS read-only
			STATUS mandatory
			DESCRIPTION
				"Instance number of this battery entry."
			::= { batteryEntry 1 }

		
		-- 1.3.6.1.4.1.674.10893.1.20.130.15.1.2
		batteryName OBJECT-TYPE
			SYNTAX DisplayString
			ACCESS read-only
			STATUS mandatory
			DESCRIPTION
				"The battery's name as represented in Storage Management."
			::= { batteryEntry 2 }

		
		-- 1.3.6.1.4.1.674.10893.1.20.130.15.1.3
		batteryVendor OBJECT-TYPE
			SYNTAX DisplayString
			ACCESS read-only
			STATUS mandatory
			DESCRIPTION
				"The battery's (re)seller's name."
			::= { batteryEntry 3 }

		
		-- 1.3.6.1.4.1.674.10893.1.20.130.15.1.4
		batteryState OBJECT-TYPE
			SYNTAX INTEGER
				{
				ready(1),
				failed(2),
				degraded(6),
				reconditioning(7),
				high(9),
				low(10),
				charging(12),
				missing(21),
				learning(36)
				}
			ACCESS read-only
			STATUS mandatory
			DESCRIPTION
				"Current state of battery.
				Possible values:
				 0: Unknown
				 1: Ready
				 2: Failed
				 6: Degraded
				 7: Reconditioning 
				 9: High
				10: Low Power
				12: Charging
				21: Missing
				36: Learning
				"
			::= { batteryEntry 4 }

		
		-- 1.3.6.1.4.1.674.10893.1.20.130.15.1.5
		batteryRollUpStatus OBJECT-TYPE
			SYNTAX DellStatus
			ACCESS read-only
			STATUS mandatory
			DESCRIPTION
				"Severity of the battery state.
				This is the combined status of the battery and its components.
				Possible values:
				1: Other
				2: Unknown
				3: OK 
				4: Non-critical 
				5: Critical
				6: Non-recoverable"
			::= { batteryEntry 5 }

		
		-- 1.3.6.1.4.1.674.10893.1.20.130.15.1.6
		batteryComponentStatus OBJECT-TYPE
			SYNTAX DellStatus
			ACCESS read-only
			STATUS mandatory
			DESCRIPTION
				"The status of the battery itself without the 
				propagation of any contained component status.
				Possible values:
				1: Other
				2: Unknown
				3: OK 
				4: Non-critical 
				5: Critical
				6: Non-recoverable"
			::= { batteryEntry 6 }

		
		-- 1.3.6.1.4.1.674.10893.1.20.130.15.1.7
		batteryChargeCount OBJECT-TYPE
			SYNTAX INTEGER
			ACCESS read-only
			STATUS mandatory
			DESCRIPTION
				"The number of charges that have been applied to the battery."
			::= { batteryEntry 7 }

		
		-- 1.3.6.1.4.1.674.10893.1.20.130.15.1.8
		batteryMaxChargeCount OBJECT-TYPE
			SYNTAX INTEGER
			ACCESS read-only
			STATUS mandatory
			DESCRIPTION
				"The maximum number of charges that can be applied to the battery."
			::= { batteryEntry 8 }

		
		-- 1.3.6.1.4.1.674.10893.1.20.130.15.1.9
		batteryNexusID OBJECT-TYPE
			SYNTAX DisplayString
			ACCESS read-only
			STATUS mandatory
			DESCRIPTION
				"Durable unique ID for this battery."
			::= { batteryEntry 9 }

		
		-- 1.3.6.1.4.1.674.10893.1.20.130.15.1.10
		batteryPredictedCapacity OBJECT-TYPE
			SYNTAX INTEGER
				{
				failed(1),
				ready(2),
				unknown(4)
				}
			ACCESS read-only
			STATUS mandatory
			DESCRIPTION
				"This property displays the battery's ability to be charged.
				Possible values:
				1: Failed   - The battery cannot be charged and needs to be replaced.
				2: Ready    - The battery can be charged to full capacity.
				4: Unknown  - The battery is completing a Learn cycle. The charge capacity of the battery cannot be determined until the Learn cycle is complete.
				"
			::= { batteryEntry 10 }

		
		-- 1.3.6.1.4.1.674.10893.1.20.130.15.1.11
		batteryNextLearnTime OBJECT-TYPE
			SYNTAX INTEGER
			ACCESS read-only
			STATUS mandatory
			DESCRIPTION
				"Time next learn cycle must be executed (in hours.)
				"
			::= { batteryEntry 11 }

		
		-- 1.3.6.1.4.1.674.10893.1.20.130.15.1.12
		batteryLearnState OBJECT-TYPE
			SYNTAX INTEGER
				{
				failed(1),
				active(2),
				timedOut(4),
				requested(8),
				idle(16)
				}
			ACCESS read-only
			STATUS mandatory
			DESCRIPTION
				"Specifies the learn state activity of the battery.
				Possible values:
				1 : Failed
				2 : Active
				4 : Timed out
				8 : Requested
				16: Idle"
			::= { batteryEntry 12 }

		
		-- 1.3.6.1.4.1.674.10893.1.20.130.15.1.14
		batteryMaxLearnDelay OBJECT-TYPE
			SYNTAX INTEGER
			ACCESS read-only
			STATUS mandatory
			DESCRIPTION
				"The maximum amount of time (in hours) that the battery learn cycle can be delayed."
			::= { batteryEntry 14 }

		
		-- 1.3.6.1.4.1.674.10893.1.20.130.16
		batteryConnectionTable OBJECT-TYPE
			SYNTAX SEQUENCE OF BatteryConnectionEntry
			ACCESS not-accessible
			STATUS mandatory
			DESCRIPTION
				"A table of the connections between each 
				battery on the managed node and its controller. 
				Each controller number in the table corresponds to that 
				controller instance in the Controller Table."
			::= { physicalDevices 16 }

		
		-- 1.3.6.1.4.1.674.10893.1.20.130.16.1
		batteryConnectionEntry OBJECT-TYPE
			SYNTAX BatteryConnectionEntry
			ACCESS not-accessible
			STATUS mandatory
			DESCRIPTION
				"An entry in the Battery Connection table . A row in this table cannot be
				created or deleted by SNMP operations on columns of the table."
			INDEX { batteryConnectionNumber }
			::= { batteryConnectionTable 1 }

		
		BatteryConnectionEntry ::=
			SEQUENCE { 
				batteryConnectionNumber
					INTEGER,
				batteryConnectionBatteryName
					DisplayString,
				batteryConnectionBatteryNumber
					INTEGER,
				batteryConnectionControllerName
					DisplayString,
				batteryConnectionControllerNumber
					INTEGER
			 }

		-- 1.3.6.1.4.1.674.10893.1.20.130.16.1.1
		batteryConnectionNumber OBJECT-TYPE
			SYNTAX INTEGER (1..255)
			ACCESS read-only
			STATUS mandatory
			DESCRIPTION
				"Instance number of this battery connection entry."
			::= { batteryConnectionEntry 1 }

		
		-- 1.3.6.1.4.1.674.10893.1.20.130.16.1.2
		batteryConnectionBatteryName OBJECT-TYPE
			SYNTAX DisplayString
			ACCESS read-only
			STATUS mandatory
			DESCRIPTION
				"The name of the battery in this connection as represented in Storage Management."
			::= { batteryConnectionEntry 2 }

		
		-- 1.3.6.1.4.1.674.10893.1.20.130.16.1.3
		batteryConnectionBatteryNumber OBJECT-TYPE
			SYNTAX INTEGER
			ACCESS read-only
			STATUS mandatory
			DESCRIPTION
				"The instance number in the batteryTable of the battery in this connection."
			::= { batteryConnectionEntry 3 }

		
		-- 1.3.6.1.4.1.674.10893.1.20.130.16.1.4
		batteryConnectionControllerName OBJECT-TYPE
			SYNTAX DisplayString
			ACCESS read-only
			STATUS mandatory
			DESCRIPTION
				"The name of the controller as represented in Storage Management
				to which this battery belongs."
			::= { batteryConnectionEntry 4 }

		
		-- 1.3.6.1.4.1.674.10893.1.20.130.16.1.5
		batteryConnectionControllerNumber OBJECT-TYPE
			SYNTAX INTEGER
			ACCESS read-only
			STATUS mandatory
			DESCRIPTION
				"The instance number of the controller in the controllerTable
				to which this battery belongs."
			::= { batteryConnectionEntry 5 }

		
		-- 1.3.6.1.4.1.674.10893.1.20.140
		logicalDevices OBJECT IDENTIFIER ::= { storageManagement 140 }

		
		-- 1.3.6.1.4.1.674.10893.1.20.140.3
		arrayDiskLogicalConnectionTable OBJECT-TYPE
			SYNTAX SEQUENCE OF ArrayDiskLogicalConnectionEntry
			ACCESS not-accessible
			STATUS mandatory
			DESCRIPTION
				"A table of the connections between array disks, the 
				virtual disk to which they belong, and their
				associated logical disk. For each object in the table, 
				its object number corresponds to an instance number in 
				the appropriate MIB table for that object where all of 
				the object properties can be found.
				
				         
				"
			::= { logicalDevices 3 }

		
		-- 1.3.6.1.4.1.674.10893.1.20.140.3.1
		arrayDiskLogicalConnectionEntry OBJECT-TYPE
			SYNTAX ArrayDiskLogicalConnectionEntry
			ACCESS not-accessible
			STATUS mandatory
			DESCRIPTION
				"An entry in the Array Disk Logical Connection table . A row in this table 
				cannot be created or deleted by SNMP operations on columns of the table."
			INDEX { arrayDiskLogicalConnectionNumber }
			::= { arrayDiskLogicalConnectionTable 1 }

		
		ArrayDiskLogicalConnectionEntry ::=
			SEQUENCE { 
				arrayDiskLogicalConnectionNumber
					INTEGER,
				arrayDiskLogicalConnectionArrayDiskName
					DisplayString,
				arrayDiskLogicalConnectionArrayDiskNumber
					INTEGER,
				arrayDiskLogicalConnectionVirtualDiskName
					DisplayString,
				arrayDiskLogicalConnectionVirtualDiskNumber
					INTEGER,
				arrayDiskLogicalConnectionDiskName
					DisplayString,
				arrayDiskLogicalConnectionDiskNumber
					INTEGER
			 }

		-- 1.3.6.1.4.1.674.10893.1.20.140.3.1.1
		arrayDiskLogicalConnectionNumber OBJECT-TYPE
			SYNTAX INTEGER (1..1000000000)
			ACCESS read-only
			STATUS mandatory
			DESCRIPTION
				"Instance number of this array disk logical connection entry."
			::= { arrayDiskLogicalConnectionEntry 1 }

		
		-- 1.3.6.1.4.1.674.10893.1.20.140.3.1.2
		arrayDiskLogicalConnectionArrayDiskName OBJECT-TYPE
			SYNTAX DisplayString
			ACCESS read-only
			STATUS mandatory
			DESCRIPTION
				"The name of the array disk in this logical connection."
			::= { arrayDiskLogicalConnectionEntry 2 }

		
		-- 1.3.6.1.4.1.674.10893.1.20.140.3.1.3
		arrayDiskLogicalConnectionArrayDiskNumber OBJECT-TYPE
			SYNTAX INTEGER
			ACCESS read-only
			STATUS mandatory
			DESCRIPTION
				"The instance number of the array disk in this logical connection."
			::= { arrayDiskLogicalConnectionEntry 3 }

		
		-- 1.3.6.1.4.1.674.10893.1.20.140.3.1.4
		arrayDiskLogicalConnectionVirtualDiskName OBJECT-TYPE
			SYNTAX DisplayString
			ACCESS read-only
			STATUS mandatory
			DESCRIPTION
				"The name of the virtual disk to which this array disk belongs."
			::= { arrayDiskLogicalConnectionEntry 4 }

		
		-- 1.3.6.1.4.1.674.10893.1.20.140.3.1.5
		arrayDiskLogicalConnectionVirtualDiskNumber OBJECT-TYPE
			SYNTAX INTEGER
			ACCESS read-only
			STATUS mandatory
			DESCRIPTION
				"The instance number of the virtual disk to which this array disk 
				belongs."
			::= { arrayDiskLogicalConnectionEntry 5 }

		
		-- 1.3.6.1.4.1.674.10893.1.20.140.3.1.6
		arrayDiskLogicalConnectionDiskName OBJECT-TYPE
			SYNTAX DisplayString
			ACCESS read-only
			STATUS mandatory
			DESCRIPTION
				"The name of the disk group to with this array disk belongs.
				This property is currently not supported."
			::= { arrayDiskLogicalConnectionEntry 6 }

		
		-- 1.3.6.1.4.1.674.10893.1.20.140.3.1.7
		arrayDiskLogicalConnectionDiskNumber OBJECT-TYPE
			SYNTAX INTEGER
			ACCESS read-only
			STATUS mandatory
			DESCRIPTION
				"This instance number of the disk group to with this array disk belongs.
				This property is currently not supported."
			::= { arrayDiskLogicalConnectionEntry 7 }

		
		-- 1.3.6.1.4.1.674.10893.1.20.140.1
		virtualDiskTable OBJECT-TYPE
			SYNTAX SEQUENCE OF VirtualDiskEntry
			ACCESS not-accessible
			STATUS mandatory
			DESCRIPTION
				"A table of managed Virtual Disks. The number of entries is related
				to number of Virtual Disks discovered in the system. 
				The maximum number of entries is implementation dependent.
				Note: The properties in this table may not be applicable to all entries."
			::= { logicalDevices 1 }

		
		-- 1.3.6.1.4.1.674.10893.1.20.140.1.1
		virtualDiskEntry OBJECT-TYPE
			SYNTAX VirtualDiskEntry
			ACCESS not-accessible
			STATUS mandatory
			DESCRIPTION
				"An entry in the Virtual Disk table. A row in this table cannot be
				created or deleted by SNMP operations on columns of the table."
			INDEX { virtualDiskNumber }
			::= { virtualDiskTable 1 }

		
		VirtualDiskEntry ::=
			SEQUENCE { 
				virtualDiskNumber
					INTEGER,
				virtualDiskName
					DisplayString,
				virtualDiskDeviceName
					DisplayString,
				virtualDiskState
					INTEGER,
				virtualDiskSeverity
					INTEGER,
				virtualDiskLengthInMB
					INTEGER,
				virtualDiskLengthInBytes
					INTEGER,
				virtualDiskFreeSpaceInMB
					INTEGER,
				virtualDiskFreeSpaceInBytes
					INTEGER,
				virtualDiskWritePolicy
					INTEGER,
				virtualDiskReadPolicy
					INTEGER,
				virtualDiskCachePolicy
					INTEGER,
				virtualDiskLayout
					INTEGER,
				virtualDiskCurStripeSizeInMB
					INTEGER,
				virtualDiskCurStripeSizeInBytes
					INTEGER,
				virtualDiskChannel
					INTEGER,
				virtualDiskTargetID
					INTEGER,
				virtualDiskLunID
					INTEGER,
				virtualDiskRollUpStatus
					DellStatus,
				virtualDiskComponentStatus
					DellStatus,
				virtualDiskNexusID
					DisplayString,
				virtualDiskArrayDiskType
					INTEGER
			 }

		-- 1.3.6.1.4.1.674.10893.1.20.140.1.1.1
		virtualDiskNumber OBJECT-TYPE
			SYNTAX INTEGER (1..100000000)
			ACCESS read-only
			STATUS mandatory
			DESCRIPTION
				"Instance number of this virtual disk entry."
			::= { virtualDiskEntry 1 }

		
		-- 1.3.6.1.4.1.674.10893.1.20.140.1.1.2
		virtualDiskName OBJECT-TYPE
			SYNTAX DisplayString
			ACCESS read-only
			STATUS mandatory
			DESCRIPTION
				"The virtual disk's label generated by Storage Management or entered
				by the user."
			::= { virtualDiskEntry 2 }

		
		-- 1.3.6.1.4.1.674.10893.1.20.140.1.1.3
		virtualDiskDeviceName OBJECT-TYPE
			SYNTAX DisplayString
			ACCESS read-only
			STATUS mandatory
			DESCRIPTION
				"Device name used by this virtual disk's member disks."
			::= { virtualDiskEntry 3 }

		
		-- 1.3.6.1.4.1.674.10893.1.20.140.1.1.4
		virtualDiskState OBJECT-TYPE
			SYNTAX INTEGER
				{
				ready(1),
				failed(2),
				online(3),
				offline(4),
				degraded(6),
				verifying(7),
				resynching(15),
				regenerating(16),
				failedRedundancy(18),
				rebuilding(24),
				formatting(26),
				reconstructing(32),
				initializing(35),
				backgroundInit(36),
				permanentlyDegraded(52)
				}
			ACCESS read-only
			STATUS mandatory
			DESCRIPTION
				"The current condition of this virtual disk
				(which includes any member array disks.)
				Possible states:
				 0: Unknown
				 1: Ready - The disk is accessible and has no known problems. 
				 2: Failed - Access has been lost to the data or is about to be lost.
				 3: Online
				 4: Offline - The disk is not accessible. The disk may be corrupted or intermittently unavailable. 
				 6: Degraded - The data on the virtual disk is no longer fault tolerant because one of the underlying disks is not online.
				15: Resynching
				16: Regenerating
				24: Rebuilding
				26: Formatting
				32: Reconstructing
				35: Initializing
				36: Background Initialization
				38: Resynching Paused
				52: Permanently Degraded
				54: Degraded Redundancy"
			::= { virtualDiskEntry 4 }

		
		-- 1.3.6.1.4.1.674.10893.1.20.140.1.1.5
		virtualDiskSeverity OBJECT-TYPE
			SYNTAX INTEGER
				{
				warning(1),
				error(2),
				failure(3)
				}
			ACCESS read-only
			STATUS obsolete
			DESCRIPTION
				"This entry is obsolete for Storage Management.
				It was replaced with RollUpStatus and ComponentStatus for each device."
			::= { virtualDiskEntry 5 }

		
		-- 1.3.6.1.4.1.674.10893.1.20.140.1.1.6
		virtualDiskLengthInMB OBJECT-TYPE
			SYNTAX INTEGER
			ACCESS read-only
			STATUS mandatory
			DESCRIPTION
				"The size of this virtual disk in megabytes.  If this size
				is 0, it is smaller than a megabyte."
			::= { virtualDiskEntry 6 }

		
		-- 1.3.6.1.4.1.674.10893.1.20.140.1.1.7
		virtualDiskLengthInBytes OBJECT-TYPE
			SYNTAX INTEGER
			ACCESS read-only
			STATUS mandatory
			DESCRIPTION
				"The portion of the virtual disk in bytes that is smaller
				than a megabyte.  This size plus the virtualDiskLengthInMB
				is the total size of the virtual disk."
			::= { virtualDiskEntry 7 }

		
		-- 1.3.6.1.4.1.674.10893.1.20.140.1.1.8
		virtualDiskFreeSpaceInMB OBJECT-TYPE
			SYNTAX INTEGER
			ACCESS read-only
			STATUS obsolete
			DESCRIPTION
				"This entry is obsolete. This property is not supported for virtual disks managed under Storage Management."
			::= { virtualDiskEntry 8 }

		
		-- 1.3.6.1.4.1.674.10893.1.20.140.1.1.9
		virtualDiskFreeSpaceInBytes OBJECT-TYPE
			SYNTAX INTEGER
			ACCESS read-only
			STATUS obsolete
			DESCRIPTION
				"This entry is obsolete. This property is not supported for virtual disks managed under Storage Management."
			::= { virtualDiskEntry 9 }

		
		-- 1.3.6.1.4.1.674.10893.1.20.140.1.1.10
		virtualDiskWritePolicy OBJECT-TYPE
			SYNTAX INTEGER
				{
				enabled(1),
				disabled(2),
				writeBack(3),
				writeThrough(4),
				enabledAlways(5),
				enabledAlwaysSAS(6)
				}
			ACCESS read-only
			STATUS mandatory
			DESCRIPTION
				"Indicates whether the controller's write cache will be used 
				when writing to a virtual disk.
				Possible values:
				1: Enabled - Adaptec Write Cache Enabled Protected
				2: Disabled - Adaptec Write Cache Disabled
				3: LSI Write Back
				4: LSI Write Through
				5: Enabled Always - Adaptec only
				6: Enabled Always - SAS only"
			::= { virtualDiskEntry 10 }

		
		-- 1.3.6.1.4.1.674.10893.1.20.140.1.1.11
		virtualDiskReadPolicy OBJECT-TYPE
			SYNTAX INTEGER
				{
				enabled(1),
				disabled(2),
				readAhead(3),
				adaptiveReadAhead(4),
				noReadAhead(5)
				}
			ACCESS read-only
			STATUS mandatory
			DESCRIPTION
				"Indicates whether the controller's read cache will be used 
				when reading from a virtual disk.
				Possible values:
				1: Enabled - Adaptec Read Cache Enabled
				2: Disabled - Adaptec Read Cache Disabled
				3: LSI Read Ahead
				4: LSI Adaptive Read Ahead
				5: LSI No Read Ahead"
			::= { virtualDiskEntry 11 }

		
		-- 1.3.6.1.4.1.674.10893.1.20.140.1.1.12
		virtualDiskCachePolicy OBJECT-TYPE
			SYNTAX INTEGER
				{
				directIO(1),
				cachedIO(2),
				not-applicable(99)
				}
			ACCESS read-only
			STATUS mandatory
			DESCRIPTION
				"Indicates whether the controller's cache is used when 
				reading from or writing to a virtual disk.
				Possible values:
				 1: Direct I/O (LSI)
				 2: Cached I/O (LSI)
				99: Not applicable"
			::= { virtualDiskEntry 12 }

		
		-- 1.3.6.1.4.1.674.10893.1.20.140.1.1.13
		virtualDiskLayout OBJECT-TYPE
			SYNTAX INTEGER
				{
				concatenated(1),
				raid-0(2),
				raid-1(3),
				raid-2(4),
				raid-3(5),
				raid-4(6),
				raid-5(7),
				raid-6(8),
				raid-7(9),
				raid-10(10),
				raid-30(11),
				raid-50(12),
				addSpares(13),
				deleteLogical(14),
				transformLogical(15),
				raid-0-plus-1(18),
				concatRaid-1(19),
				concatRaid-5(20),
				noRaid(21),
				volume(22),
				raidMorph(23),
				raid-60(24)
				}
			ACCESS read-only
			STATUS mandatory
			DESCRIPTION
				"The virtual disk's RAID type.
				Currently supported types:
				 1: Concatenated
				 2: RAID-0
				 3: RAID-1
				 7: RAID-5
				 8: RAID-6
				10: RAID-10
				12: RAID-50
				19: Concatenated RAID 1
				24: RAID-60
				"
			::= { virtualDiskEntry 13 }

		
		-- 1.3.6.1.4.1.674.10893.1.20.140.1.1.14
		virtualDiskCurStripeSizeInMB OBJECT-TYPE
			SYNTAX INTEGER
			ACCESS read-only
			STATUS mandatory
			DESCRIPTION
				"The stripe size of this virtual disk in megabytes.  If this
				size is 0, it is either smaller than a megabyte or not applicable.
				"
			::= { virtualDiskEntry 14 }

		
		-- 1.3.6.1.4.1.674.10893.1.20.140.1.1.15
		virtualDiskCurStripeSizeInBytes OBJECT-TYPE
			SYNTAX INTEGER
			ACCESS read-only
			STATUS mandatory
			DESCRIPTION
				"The portion of the stripe size in bytes that is smaller 
				than a megabyte.  This size plus the virtualDiskCurStripeSizeInMB
				is the total stripe size on the virtual disk.
				If this size is 0, either the entire size is whole megabytes or it is not applicable."
			::= { virtualDiskEntry 15 }

		
		-- 1.3.6.1.4.1.674.10893.1.20.140.1.1.16
		virtualDiskChannel OBJECT-TYPE
			SYNTAX INTEGER
			ACCESS read-only
			STATUS obsolete
			DESCRIPTION
				"This entry is obsolete. This property is not supported
				by virtual disks managed under Storage Management."
			::= { virtualDiskEntry 16 }

		
		-- 1.3.6.1.4.1.674.10893.1.20.140.1.1.17
		virtualDiskTargetID OBJECT-TYPE
			SYNTAX INTEGER
			ACCESS read-only
			STATUS mandatory
			DESCRIPTION
				"Unique ID for the virtual disk."
			::= { virtualDiskEntry 17 }

		
		-- 1.3.6.1.4.1.674.10893.1.20.140.1.1.18
		virtualDiskLunID OBJECT-TYPE
			SYNTAX INTEGER
			ACCESS read-only
			STATUS obsolete
			DESCRIPTION
				"This entry is obsolete. This property is not supported
				by virtual disks managed under Storage Management."
			::= { virtualDiskEntry 18 }

		
		-- 1.3.6.1.4.1.674.10893.1.20.140.1.1.19
		virtualDiskRollUpStatus OBJECT-TYPE
			SYNTAX DellStatus
			ACCESS read-only
			STATUS mandatory
			DESCRIPTION
				"Severity of the virtual disk state.
				This is the combined status of the virtual disk and its 
				components.
				Possible values:
				1: Other
				2: Unknown
				3: OK 
				4: Non-critical 
				5: Critical
				6: Non-recoverable"
			::= { virtualDiskEntry 19 }

		
		-- 1.3.6.1.4.1.674.10893.1.20.140.1.1.20
		virtualDiskComponentStatus OBJECT-TYPE
			SYNTAX DellStatus
			ACCESS read-only
			STATUS mandatory
			DESCRIPTION
				"The status of the virtual disk itself without 
				the propagation of any contained component status.
				Possible values:
				1: Other
				2: Unknown
				3: OK 
				4: Non-critical 
				5: Critical
				6: Non-recoverable"
			::= { virtualDiskEntry 20 }

		
		-- 1.3.6.1.4.1.674.10893.1.20.140.1.1.21
		virtualDiskNexusID OBJECT-TYPE
			SYNTAX DisplayString
			ACCESS read-only
			STATUS mandatory
			DESCRIPTION
				"Durable unique ID for this virtual disk."
			::= { virtualDiskEntry 21 }

		
		-- 1.3.6.1.4.1.674.10893.1.20.140.1.1.22
		virtualDiskArrayDiskType OBJECT-TYPE
			SYNTAX INTEGER
				{
				sas(1),
				sata(2),
				scsi(3),
				ide(4),
				unknown(99)
				}
			ACCESS read-only
			STATUS mandatory
			DESCRIPTION
				"Identifies the type of array (physical) disks used to create the virtual disk.
				Possible values:
				 1: SAS
				 2: SATA
				 3: SCSI
				 4: IDE
				99: Unknown
				"
			::= { virtualDiskEntry 22 }

		
		-- 1.3.6.1.4.1.674.10893.1.20.200
		storageManagementEvent OBJECT IDENTIFIER ::= { storageManagement 200 }

		
		-- 1.3.6.1.4.1.674.10893.1.20.200.1
		messageIDEvent OBJECT-TYPE
			SYNTAX INTEGER
			ACCESS read-only
			STATUS mandatory
			DESCRIPTION
				"0200.0001 Storage Management alert (event) message number."
			::= { storageManagementEvent 1 }

		
		-- 1.3.6.1.4.1.674.10893.1.20.200.2
		descriptionEvent OBJECT-TYPE
			SYNTAX DisplayString (SIZE (1..64))
			ACCESS read-only
			STATUS mandatory
			DESCRIPTION
				"0200.0002 Storage Management event message text describing the alert."
			::= { storageManagementEvent 2 }

		
		-- 1.3.6.1.4.1.674.10893.1.20.200.3
		locationEvent OBJECT-TYPE
			SYNTAX DisplayString
			ACCESS read-only
			STATUS mandatory
			DESCRIPTION
				"0200.0003 Additional information identifying the location of the object causing the alert."
			::= { storageManagementEvent 3 }

		
		-- 1.3.6.1.4.1.674.10893.1.20.200.4
		objectNameEvent OBJECT-TYPE
			SYNTAX DisplayString
			ACCESS read-only
			STATUS mandatory
			DESCRIPTION
				"0200.0004 Name of the object as represented in Storage Management causing the alert."
			::= { storageManagementEvent 4 }

		
		-- 1.3.6.1.4.1.674.10893.1.20.200.5
		objectOIDEvent OBJECT-TYPE
			SYNTAX DisplayString (SIZE (1..64))
			ACCESS read-only
			STATUS mandatory
			DESCRIPTION
				"0200.0005 MIB OID of the object causing the alert."
			::= { storageManagementEvent 5 }

		
		-- 1.3.6.1.4.1.674.10893.1.20.200.6
		objectNexusEvent OBJECT-TYPE
			SYNTAX DisplayString (SIZE (1..64))
			ACCESS read-only
			STATUS mandatory
			DESCRIPTION
				"0200.0006 Durable, unique ID of the object causing the alert."
			::= { storageManagementEvent 6 }

		
		-- 1.3.6.1.4.1.674.10893.1.20.200.7
		currentStatusEvent OBJECT-TYPE
			SYNTAX DellStatus
			ACCESS read-only
			STATUS mandatory
			DESCRIPTION
				"0200.0007 Current status of object causing the alert, if applicable."
			::= { storageManagementEvent 7 }

		
		-- 1.3.6.1.4.1.674.10893.1.20.200.8
		previousStatusEvent OBJECT-TYPE
			SYNTAX DellStatus
			ACCESS read-only
			STATUS mandatory
			DESCRIPTION
				"0200.0008 Previous status of object causing the alert if applicable."
			::= { storageManagementEvent 8 }

		
	
--
-- Trap definitions
--
	
		alertStorageManagementInformation TRAP-TYPE 
			ENTERPRISE storageManagementEvent
			VARIABLES { messageIDEvent, descriptionEvent }
			DESCRIPTION 
				"Storage Management Information
				There is no global status change associated with this trap."
--#TYPE      "Storage Management Event: Storage Management Information"
--#SEVERITY  INFORMATIONAL
--#SUMMARY   "Alert message ID: %s, Storage Management information. %s"
--#ARGUMENTS { 0, 1 }
--#CATEGORY  "Status Events"
--#STATE     OPERATIONAL
--#STATUS    MANDATORY
			::=  101
		alertStorageManagementNormal TRAP-TYPE 
			ENTERPRISE storageManagementEvent
			VARIABLES { messageIDEvent, descriptionEvent }
			DESCRIPTION 
				"There is no global status change associated with this trap."
--#TYPE      "Storage Management Event: Storage Management Normal"
--#SEVERITY  INFORMATIONAL
--#SUMMARY   "Alert message ID: %s, %s"
--#ARGUMENTS { 0, 1 }
--#CATEGORY  "Status Events"
--#STATE     OPERATIONAL
--#STATUS    MANDATORY
			::=  102
		alertStorageManagementWarning TRAP-TYPE 
			ENTERPRISE storageManagementEvent
			VARIABLES { messageIDEvent, descriptionEvent }
			DESCRIPTION 
				"Storage Management has detected a device independent warning condition.
				There is no global status change associated with this trap."
--#TYPE      "Storage Management Event: Storage Management Warning"
--#SEVERITY  MINOR
--#SUMMARY   "Alert message ID: %s, Storage Management has detected a device independent warning condition. %s"
--#ARGUMENTS { 0, 1 }
--#CATEGORY  "Status Events"
--#STATE     DEGRADED
--#STATUS    MANDATORY
			::=  103
		alertStorageManagementFailure TRAP-TYPE 
			ENTERPRISE storageManagementEvent
			VARIABLES { messageIDEvent, descriptionEvent }
			DESCRIPTION 
				"Storage Management has detected a device independent error condition.
				There is no global status change associated with this trap."
--#TYPE      "Storage Management Event: Storage Management Failure"
--#SEVERITY  CRITICAL
--#SUMMARY   "Alert message ID: %s, Storage Management has detected a device independent error condition. %s"
--#ARGUMENTS { 0, 1 }
--#CATEGORY  "Error Events"
--#STATE     FAILED
--#STATUS    MANDATORY
			::=  104
		alertStorageManagementNonRecoverable TRAP-TYPE 
			ENTERPRISE storageManagementEvent
			VARIABLES { messageIDEvent, descriptionEvent }
			DESCRIPTION 
				"Storage Management has detected a device independent non-recoverable condition.
				There is no global status change associated with this trap."
--#TYPE      "Storage Management Event: Storage Management Non-recoverable"
--#SEVERITY  CRITICAL
--#SUMMARY   "Alert message ID: %s, Storage Management has detected a device independent non-recoverable condition. %s"
--#ARGUMENTS { 0, 1 }
--#CATEGORY  "Error Events"
--#STATE     FAILED
--#STATUS    MANDATORY
			::=  105
		alertControllerInformation TRAP-TYPE 
			ENTERPRISE storageManagementEvent
			VARIABLES { messageIDEvent, descriptionEvent, locationEvent, objectNameEvent, objectOIDEvent, 
				objectNexusEvent, currentStatusEvent, previousStatusEvent }
			DESCRIPTION 
				"Controller information."
--#TYPE      "Storage Management Event: Controller Information"
--#SEVERITY  INFORMATIONAL
--#SUMMARY   "Alert message ID: %s, Controller information. %s, %s, %s"
--#ARGUMENTS { 0, 1, 2, 3 }
--#CATEGORY  "Status Events"
--#STATE     OPERATIONAL
--#STATUS    MANDATORY
			::=  751
		alertControllerNormal TRAP-TYPE 
			ENTERPRISE storageManagementEvent
			VARIABLES { messageIDEvent, descriptionEvent, locationEvent, objectNameEvent, objectOIDEvent, 
				objectNexusEvent, currentStatusEvent, previousStatusEvent }
			DESCRIPTION 
				"Controller has returned to normal."
--#TYPE      "Storage Management Event: Controller Normal"
--#SEVERITY  INFORMATIONAL
--#SUMMARY   "Alert message ID: %s, Controller has returned to normal. %s, %s, %s"
--#ARGUMENTS { 0, 1, 2, 3 }
--#CATEGORY  "Status Events"
--#STATE     OPERATIONAL
--#STATUS    MANDATORY
			::=  752
		alertControllerWarning TRAP-TYPE 
			ENTERPRISE storageManagementEvent
			VARIABLES { messageIDEvent, descriptionEvent, locationEvent, objectNameEvent, objectOIDEvent, 
				objectNexusEvent, currentStatusEvent, previousStatusEvent }
			DESCRIPTION 
				"Controller warning."
--#TYPE      "Storage Management Event: Controller Warning"
--#SEVERITY  MINOR
--#SUMMARY   "Alert message ID: %s, Controller warning. %s, %s, %s"
--#ARGUMENTS { 0, 1, 2, 3 }
--#CATEGORY  "Status Events"
--#STATE     DEGRADED
--#STATUS    MANDATORY
			::=  753
		alertControllerFailure TRAP-TYPE 
			ENTERPRISE storageManagementEvent
			VARIABLES { messageIDEvent, descriptionEvent, locationEvent, objectNameEvent, objectOIDEvent, 
				objectNexusEvent, currentStatusEvent, previousStatusEvent }
			DESCRIPTION 
				"Controller failure."
--#TYPE      "Storage Management Event: Controller Failure"
--#SEVERITY  CRITICAL
--#SUMMARY   "Alert message ID: %s, Controller failure. %s, %s, %s"
--#ARGUMENTS { 0, 1, 2, 3 }
--#CATEGORY  "Error Events"
--#STATE     FAILED
--#STATUS    MANDATORY
			::=  754
		alertControllerNonRecoverable TRAP-TYPE 
			ENTERPRISE storageManagementEvent
			VARIABLES { messageIDEvent, descriptionEvent, locationEvent, objectNameEvent, objectOIDEvent, 
				objectNexusEvent, currentStatusEvent, previousStatusEvent }
			DESCRIPTION 
				"Controller is non-recoverable."
--#TYPE      "Storage Management Event: Controller Non-recoverable"
--#SEVERITY  CRITICAL
--#SUMMARY   "Alert message ID: %s, Controller is non-recoverable. %s, %s, %s"
--#ARGUMENTS { 0, 1, 2, 3 }
--#CATEGORY  "Error Events"
--#STATE     FAILED
--#STATUS    MANDATORY
			::=  755
		alertChannelInformation TRAP-TYPE 
			ENTERPRISE storageManagementEvent
			VARIABLES { messageIDEvent, descriptionEvent, locationEvent, objectNameEvent, objectOIDEvent, 
				objectNexusEvent, currentStatusEvent, previousStatusEvent }
			DESCRIPTION 
				"Channel information."
--#TYPE      "Storage Management Event: Channel Information"
--#SEVERITY  INFORMATIONAL
--#SUMMARY   "Alert message ID: %s, Channel information. %s, %s, %s"
--#ARGUMENTS { 0, 1, 2, 3 }
--#CATEGORY  "Status Events"
--#STATE     OPERATIONAL
--#STATUS    MANDATORY
			::=  801
		alertChannelNormal TRAP-TYPE 
			ENTERPRISE storageManagementEvent
			VARIABLES { messageIDEvent, descriptionEvent, locationEvent, objectNameEvent, objectOIDEvent, 
				objectNexusEvent, currentStatusEvent, previousStatusEvent }
			DESCRIPTION 
				"Channel has returned to normal."
--#TYPE      "Storage Management Event: Channel Normal"
--#SEVERITY  INFORMATIONAL
--#SUMMARY   "Alert message ID: %s, Channel has returned to normal. %s, %s, %s"
--#ARGUMENTS { 0, 1, 2, 3 }
--#CATEGORY  "Status Events"
--#STATE     OPERATIONAL
--#STATUS    MANDATORY
			::=  802
		alertChannelWarning TRAP-TYPE 
			ENTERPRISE storageManagementEvent
			VARIABLES { messageIDEvent, descriptionEvent, locationEvent, objectNameEvent, objectOIDEvent, 
				objectNexusEvent, currentStatusEvent, previousStatusEvent }
			DESCRIPTION 
				"Channel warning."
--#TYPE      "Storage Management Event: Channel Warning"
--#SEVERITY  MINOR
--#SUMMARY   "Alert message ID: %s, Channel warning. %s, %s, %s"
--#ARGUMENTS { 0, 1, 2, 3 }
--#CATEGORY  "Status Events"
--#STATE     DEGRADED
--#STATUS    MANDATORY
			::=  803
		alertChannelFailure TRAP-TYPE 
			ENTERPRISE storageManagementEvent
			VARIABLES { messageIDEvent, descriptionEvent, locationEvent, objectNameEvent, objectOIDEvent, 
				objectNexusEvent, currentStatusEvent, previousStatusEvent }
			DESCRIPTION 
				"Channel failure."
--#TYPE      "Storage Management Event: Channel Failure"
--#SEVERITY  CRITICAL
--#SUMMARY   "Alert message ID: %s, Channel failure. %s, %s, %s"
--#ARGUMENTS { 0, 1, 2, 3 }
--#CATEGORY  "Error Events"
--#STATE     FAILED
--#STATUS    MANDATORY
			::=  804
		alertChannelNonRecoverable TRAP-TYPE 
			ENTERPRISE storageManagementEvent
			VARIABLES { messageIDEvent, descriptionEvent, locationEvent, objectNameEvent, objectOIDEvent, 
				objectNexusEvent, currentStatusEvent, previousStatusEvent }
			DESCRIPTION 
				"Channel is non-recoverable."
--#TYPE      "Storage Management Event: Channel Non-recoverable"
--#SEVERITY  CRITICAL
--#SUMMARY   "Alert message ID: %s, Channel is non-recoverable. %s, %s, %s"
--#ARGUMENTS { 0, 1, 2, 3 }
--#CATEGORY  "Error Events"
--#STATE     FAILED
--#STATUS    MANDATORY
			::=  805
		alertEnclosureInformation TRAP-TYPE 
			ENTERPRISE storageManagementEvent
			VARIABLES { messageIDEvent, descriptionEvent, locationEvent, objectNameEvent, objectOIDEvent, 
				objectNexusEvent, currentStatusEvent, previousStatusEvent }
			DESCRIPTION 
				"Enclosure information."
--#TYPE      "Storage Management Event: Enclosure Information"
--#SEVERITY  INFORMATIONAL
--#SUMMARY   "Alert message ID: %s, Enclosure information. %s, %s, %s"
--#ARGUMENTS { 0, 1, 2, 3 }
--#CATEGORY  "Status Events"
--#STATE     OPERATIONAL
--#STATUS    MANDATORY
			::=  851
		alertEnclosureNormal TRAP-TYPE 
			ENTERPRISE storageManagementEvent
			VARIABLES { messageIDEvent, descriptionEvent, locationEvent, objectNameEvent, objectOIDEvent, 
				objectNexusEvent, currentStatusEvent, previousStatusEvent }
			DESCRIPTION 
				"Enclosure has returned to normal."
--#TYPE      "Storage Management Event: Enclosure Normal"
--#SEVERITY  INFORMATIONAL
--#SUMMARY   "Alert message ID: %s, Enclosure has returned to normal. %s, %s, %s"
--#ARGUMENTS { 0, 1, 2, 3 }
--#CATEGORY  "Status Events"
--#STATE     OPERATIONAL
--#STATUS    MANDATORY
			::=  852
		alertEnclosureWarning TRAP-TYPE 
			ENTERPRISE storageManagementEvent
			VARIABLES { messageIDEvent, descriptionEvent, locationEvent, objectNameEvent, objectOIDEvent, 
				objectNexusEvent, currentStatusEvent, previousStatusEvent }
			DESCRIPTION 
				"Enclosure warning."
--#TYPE      "Storage Management Event: Enclosure Warning"
--#SEVERITY  MINOR
--#SUMMARY   "Alert message ID: %s, Enclosure warning. %s, %s, %s"
--#ARGUMENTS { 0, 1, 2, 3 }
--#CATEGORY  "Status Events"
--#STATE     DEGRADED
--#STATUS    MANDATORY
			::=  853
		alertEnclosureFailure TRAP-TYPE 
			ENTERPRISE storageManagementEvent
			VARIABLES { messageIDEvent, descriptionEvent, locationEvent, objectNameEvent, objectOIDEvent, 
				objectNexusEvent, currentStatusEvent, previousStatusEvent }
			DESCRIPTION 
				"Enclosure failure."
--#TYPE      "Storage Management Event: Enclosure Failure"
--#SEVERITY  CRITICAL
--#SUMMARY   "Alert message ID: %s, Enclosure failure. %s, %s, %s"
--#ARGUMENTS { 0, 1, 2, 3 }
--#CATEGORY  "Error Events"
--#STATE     FAILED
--#STATUS    MANDATORY
			::=  854
		alertEnclosureNonRecoverable TRAP-TYPE 
			ENTERPRISE storageManagementEvent
			VARIABLES { messageIDEvent, descriptionEvent, locationEvent, objectNameEvent, objectOIDEvent, 
				objectNexusEvent, currentStatusEvent, previousStatusEvent }
			DESCRIPTION 
				"Enclosure is non-recoverable."
--#TYPE      "Storage Management Event: Enclosure Non-recoverable"
--#SEVERITY  CRITICAL
--#SUMMARY   "Alert message ID: %s, Enclosure is non-recoverable. %s, %s, %s"
--#ARGUMENTS { 0, 1, 2, 3 }
--#CATEGORY  "Error Events"
--#STATE     FAILED
--#STATUS    MANDATORY
			::=  855
		alertArrayDiskInformation TRAP-TYPE 
			ENTERPRISE storageManagementEvent
			VARIABLES { messageIDEvent, descriptionEvent, locationEvent, objectNameEvent, objectOIDEvent, 
				objectNexusEvent, currentStatusEvent, previousStatusEvent }
			DESCRIPTION 
				"Array disk information."
--#TYPE      "Storage Management Event: Array Disk Information"
--#SEVERITY  INFORMATIONAL
--#SUMMARY   "Alert message ID: %s, Array disk information. %s, %s, %s"
--#ARGUMENTS { 0, 1, 2, 3 }
--#CATEGORY  "Status Events"
--#STATE     OPERATIONAL
--#STATUS    MANDATORY
			::=  901
		alertArrayDiskNormal TRAP-TYPE 
			ENTERPRISE storageManagementEvent
			VARIABLES { messageIDEvent, descriptionEvent, locationEvent, objectNameEvent, objectOIDEvent, 
				objectNexusEvent, currentStatusEvent, previousStatusEvent }
			DESCRIPTION 
				"Array disk has returned to normal."
--#TYPE      "Storage Management Event: Array Disk Normal"
--#SEVERITY  INFORMATIONAL
--#SUMMARY   "Alert message ID: %s, Array disk has returned to normal. %s, %s, %s"
--#ARGUMENTS { 0, 1, 2, 3 }
--#CATEGORY  "Status Events"
--#STATE     OPERATIONAL
--#STATUS    MANDATORY
			::=  902
		alertArrayDiskWarning TRAP-TYPE 
			ENTERPRISE storageManagementEvent
			VARIABLES { messageIDEvent, descriptionEvent, locationEvent, objectNameEvent, objectOIDEvent, 
				objectNexusEvent, currentStatusEvent, previousStatusEvent }
			DESCRIPTION 
				"Array disk warning."
--#TYPE      "Storage Management Event: Array Disk Warning"
--#SEVERITY  MINOR
--#SUMMARY   "Alert message ID: %s, Array disk warning. %s, %s, %s"
--#ARGUMENTS { 0, 1, 2, 3 }
--#CATEGORY  "Status Events"
--#STATE     DEGRADED
--#STATUS    MANDATORY
			::=  903
		alertArrayDiskFailure TRAP-TYPE 
			ENTERPRISE storageManagementEvent
			VARIABLES { messageIDEvent, descriptionEvent, locationEvent, objectNameEvent, objectOIDEvent, 
				objectNexusEvent, currentStatusEvent, previousStatusEvent }
			DESCRIPTION 
				"Array disk failure."
--#TYPE      "Storage Management Event: Array Disk Failure"
--#SEVERITY  CRITICAL
--#SUMMARY   "Alert message ID: %s, Array disk failure. %s, %s, %s"
--#ARGUMENTS { 0, 1, 2, 3 }
--#CATEGORY  "Error Events"
--#STATE     FAILED
--#STATUS    MANDATORY
			::=  904
		alertArrayDiskNonRecoverable TRAP-TYPE 
			ENTERPRISE storageManagementEvent
			VARIABLES { messageIDEvent, descriptionEvent, locationEvent, objectNameEvent, objectOIDEvent, 
				objectNexusEvent, currentStatusEvent, previousStatusEvent }
			DESCRIPTION 
				"Array disk is non-recoverable."
--#TYPE      "Storage Management Event: Array Disk Non-recoverable"
--#SEVERITY  CRITICAL
--#SUMMARY   "Alert message ID: %s, Array disk is non-recoverable. %s, %s, %s"
--#ARGUMENTS { 0, 1, 2, 3 }
--#CATEGORY  "Error Events"
--#STATE     FAILED
--#STATUS    MANDATORY
			::=  905
		alertEMMInformation TRAP-TYPE 
			ENTERPRISE storageManagementEvent
			VARIABLES { messageIDEvent, descriptionEvent, locationEvent, objectNameEvent, objectOIDEvent, 
				objectNexusEvent, currentStatusEvent, previousStatusEvent }
			DESCRIPTION 
				"EMM information."
--#TYPE      "Storage Management Event: EMM Information"
--#SEVERITY  INFORMATIONAL
--#SUMMARY   "Alert message ID: %s, EMM information. %s, %s, %s"
--#ARGUMENTS { 0, 1, 2, 3 }
--#CATEGORY  "Status Events"
--#STATE     OPERATIONAL
--#STATUS    MANDATORY
			::=  951
		alertEMMNormal TRAP-TYPE 
			ENTERPRISE storageManagementEvent
			VARIABLES { messageIDEvent, descriptionEvent, locationEvent, objectNameEvent, objectOIDEvent, 
				objectNexusEvent, currentStatusEvent, previousStatusEvent }
			DESCRIPTION 
				"EMM has returned to normal."
--#TYPE      "Storage Management Event: EMM Normal"
--#SEVERITY  INFORMATIONAL
--#SUMMARY   "Alert message ID: %s, EMM has returned to normal. %s, %s, %s"
--#ARGUMENTS { 0, 1, 2, 3 }
--#CATEGORY  "Status Events"
--#STATE     OPERATIONAL
--#STATUS    MANDATORY
			::=  952
		alertEMMWarning TRAP-TYPE 
			ENTERPRISE storageManagementEvent
			VARIABLES { messageIDEvent, descriptionEvent, locationEvent, objectNameEvent, objectOIDEvent, 
				objectNexusEvent, currentStatusEvent, previousStatusEvent }
			DESCRIPTION 
				"EMM warning."
--#TYPE      "Storage Management Event: EMM Warning"
--#SEVERITY  MINOR
--#SUMMARY   "Alert message ID: %s, EMM warning. %s, %s, %s"
--#ARGUMENTS { 0, 1, 2, 3 }
--#CATEGORY  "Status Events"
--#STATE     DEGRADED
--#STATUS    MANDATORY
			::=  953
		alertEMMFailure TRAP-TYPE 
			ENTERPRISE storageManagementEvent
			VARIABLES { messageIDEvent, descriptionEvent, locationEvent, objectNameEvent, objectOIDEvent, 
				objectNexusEvent, currentStatusEvent, previousStatusEvent }
			DESCRIPTION 
				"EMM failure."
--#TYPE      "Storage Management Event: EMM Failure"
--#SEVERITY  CRITICAL
--#SUMMARY   "Alert message ID: %s, EMM failure. %s, %s, %s"
--#ARGUMENTS { 0, 1, 2, 3 }
--#CATEGORY  "Error Events"
--#STATE     FAILED
--#STATUS    MANDATORY
			::=  954
		alertEMMNonRecoverable TRAP-TYPE 
			ENTERPRISE storageManagementEvent
			VARIABLES { messageIDEvent, descriptionEvent, locationEvent, objectNameEvent, objectOIDEvent, 
				objectNexusEvent, currentStatusEvent, previousStatusEvent }
			DESCRIPTION 
				"EMM is non-recoverable."
--#TYPE      "Storage Management Event: EMM Non-recoverable"
--#SEVERITY  CRITICAL
--#SUMMARY   "Alert message ID: %s, EMM is non-recoverable. %s, %s, %s"
--#ARGUMENTS { 0, 1, 2, 3 }
--#CATEGORY  "Error Events"
--#STATE     FAILED
--#STATUS    MANDATORY
			::=  955
		alertPowerSupplyInformation TRAP-TYPE 
			ENTERPRISE storageManagementEvent
			VARIABLES { messageIDEvent, descriptionEvent, locationEvent, objectNameEvent, objectOIDEvent, 
				objectNexusEvent, currentStatusEvent, previousStatusEvent }
			DESCRIPTION 
				"Power supply information."
--#TYPE      "Storage Management Event: Power Supply Information"
--#SEVERITY  INFORMATIONAL
--#SUMMARY   "Alert message ID: %s, Power supply information. %s, %s, %s"
--#ARGUMENTS { 0, 1, 2, 3 }
--#CATEGORY  "Status Events"
--#STATE     OPERATIONAL
--#STATUS    MANDATORY
			::=  1001
		alertPowerSupplyNormal TRAP-TYPE 
			ENTERPRISE storageManagementEvent
			VARIABLES { messageIDEvent, descriptionEvent, locationEvent, objectNameEvent, objectOIDEvent, 
				objectNexusEvent, currentStatusEvent, previousStatusEvent }
			DESCRIPTION 
				"Power supply has returned to normal."
--#TYPE      "Storage Management Event: Power Supply Normal"
--#SEVERITY  INFORMATIONAL
--#SUMMARY   "Alert message ID: %s, Power supply has returned to normal. %s, %s, %s"
--#ARGUMENTS { 0, 1, 2, 3 }
--#CATEGORY  "Status Events"
--#STATE     OPERATIONAL
--#STATUS    MANDATORY
			::=  1002
		alertPowerSupplyWarning TRAP-TYPE 
			ENTERPRISE storageManagementEvent
			VARIABLES { messageIDEvent, descriptionEvent, locationEvent, objectNameEvent, objectOIDEvent, 
				objectNexusEvent, currentStatusEvent, previousStatusEvent }
			DESCRIPTION 
				"Power supply warning."
--#TYPE      "Storage Management Event: Power Supply Warning"
--#SEVERITY  MINOR
--#SUMMARY   "Alert message ID: %s, Power supply warning. %s, %s, %s"
--#ARGUMENTS { 0, 1, 2, 3 }
--#CATEGORY  "Status Events"
--#STATE     DEGRADED
--#STATUS    MANDATORY
			::=  1003
		alertPowerSupplyFailure TRAP-TYPE 
			ENTERPRISE storageManagementEvent
			VARIABLES { messageIDEvent, descriptionEvent, locationEvent, objectNameEvent, objectOIDEvent, 
				objectNexusEvent, currentStatusEvent, previousStatusEvent }
			DESCRIPTION 
				"Power supply failure."
--#TYPE      "Storage Management Event: Power Supply Failure"
--#SEVERITY  CRITICAL
--#SUMMARY   "Alert message ID: %s, Power supply failure. %s, %s, %s"
--#ARGUMENTS { 0, 1, 2, 3 }
--#CATEGORY  "Error Events"
--#STATE     FAILED
--#STATUS    MANDATORY
			::=  1004
		alertPowerSupplyNonRecoverable TRAP-TYPE 
			ENTERPRISE storageManagementEvent
			VARIABLES { messageIDEvent, descriptionEvent, locationEvent, objectNameEvent, objectOIDEvent, 
				objectNexusEvent, currentStatusEvent, previousStatusEvent }
			DESCRIPTION 
				"Power supply is non-recoverable."
--#TYPE      "Storage Management Event: Power Supply Non-recoverable"
--#SEVERITY  CRITICAL
--#SUMMARY   "Alert message ID: %s, Power supply is non-recoverable. %s, %s, %s"
--#ARGUMENTS { 0, 1, 2, 3 }
--#CATEGORY  "Error Events"
--#STATE     FAILED
--#STATUS    MANDATORY
			::=  1005
		alertTemperatureProbeInformation TRAP-TYPE 
			ENTERPRISE storageManagementEvent
			VARIABLES { messageIDEvent, descriptionEvent, locationEvent, objectNameEvent, objectOIDEvent, 
				objectNexusEvent, currentStatusEvent, previousStatusEvent }
			DESCRIPTION 
				"Temperature probe information."
--#TYPE      "Storage Management Event: Temperature Probe Information"
--#SEVERITY  INFORMATIONAL
--#SUMMARY   "Alert message ID: %s, Temperature probe information. %s, %s, %s"
--#ARGUMENTS { 0, 1, 2, 3 }
--#CATEGORY  "Status Events"
--#STATE     OPERATIONAL
--#STATUS    MANDATORY
			::=  1051
		alertTemperatureProbeNormal TRAP-TYPE 
			ENTERPRISE storageManagementEvent
			VARIABLES { messageIDEvent, descriptionEvent, locationEvent, objectNameEvent, objectOIDEvent, 
				objectNexusEvent, currentStatusEvent, previousStatusEvent }
			DESCRIPTION 
				"Temperature probe has returned to normal."
--#TYPE      "Storage Management Event: Temperature Probe Normal"
--#SEVERITY  INFORMATIONAL
--#SUMMARY   "Alert message ID: %s, Temperature probe has returned to normal. %s, %s, %s"
--#ARGUMENTS { 0, 1, 2, 3 }
--#CATEGORY  "Status Events"
--#STATE     OPERATIONAL
--#STATUS    MANDATORY
			::=  1052
		alertTemperatureProbeWarning TRAP-TYPE 
			ENTERPRISE storageManagementEvent
			VARIABLES { messageIDEvent, descriptionEvent, locationEvent, objectNameEvent, objectOIDEvent, 
				objectNexusEvent, currentStatusEvent, previousStatusEvent }
			DESCRIPTION 
				"Temperature probe warning."
--#TYPE      "Storage Management Event: Temperature Probe Warning"
--#SEVERITY  MINOR
--#SUMMARY   "Alert message ID: %s, Temperature probe warning. %s, %s, %s"
--#ARGUMENTS { 0, 1, 2, 3 }
--#CATEGORY  "Status Events"
--#STATE     DEGRADED
--#STATUS    MANDATORY
			::=  1053
		alertTemperatureProbeFailure TRAP-TYPE 
			ENTERPRISE storageManagementEvent
			VARIABLES { messageIDEvent, descriptionEvent, locationEvent, objectNameEvent, objectOIDEvent, 
				objectNexusEvent, currentStatusEvent, previousStatusEvent }
			DESCRIPTION 
				"Temperature probe failure."
--#TYPE      "Storage Management Event: Temperature Probe Failure"
--#SEVERITY  CRITICAL
--#SUMMARY   "Alert message ID: %s, Temperature probe failure. %s, %s, %s"
--#ARGUMENTS { 0, 1, 2, 3 }
--#CATEGORY  "Error Events"
--#STATE     FAILED
--#STATUS    MANDATORY
			::=  1054
		alertTemperatureProbeNonRecoverable TRAP-TYPE 
			ENTERPRISE storageManagementEvent
			VARIABLES { messageIDEvent, descriptionEvent, locationEvent, objectNameEvent, objectOIDEvent, 
				objectNexusEvent, currentStatusEvent, previousStatusEvent }
			DESCRIPTION 
				"Temperature probe is non-recoverable."
--#TYPE      "Storage Management Event: Temperature Probe Non-recoverable"
--#SEVERITY  CRITICAL
--#SUMMARY   "Alert message ID: %s, Temperature probe is non-recoverable. %s, %s, %s"
--#ARGUMENTS { 0, 1, 2, 3 }
--#CATEGORY  "Error Events"
--#STATE     FAILED
--#STATUS    MANDATORY
			::=  1055
		alertFanInformation TRAP-TYPE 
			ENTERPRISE storageManagementEvent
			VARIABLES { messageIDEvent, descriptionEvent, locationEvent, objectNameEvent, objectOIDEvent, 
				objectNexusEvent, currentStatusEvent, previousStatusEvent }
			DESCRIPTION 
				"Fan information."
--#TYPE      "Storage Management Event: Fan Information"
--#SEVERITY  INFORMATIONAL
--#SUMMARY   "Alert message ID: %s, Fan information. %s, %s, %s"
--#ARGUMENTS { 0, 1, 2, 3 }
--#CATEGORY  "Status Events"
--#STATE     OPERATIONAL
--#STATUS    MANDATORY
			::=  1101
		alertFanNormal TRAP-TYPE 
			ENTERPRISE storageManagementEvent
			VARIABLES { messageIDEvent, descriptionEvent, locationEvent, objectNameEvent, objectOIDEvent, 
				objectNexusEvent, currentStatusEvent, previousStatusEvent }
			DESCRIPTION 
				"Fan has returned to normal."
--#TYPE      "Storage Management Event: Fan Normal"
--#SEVERITY  INFORMATIONAL
--#SUMMARY   "Alert message ID: %s, Fan has returned to normal. %s, %s, %s"
--#ARGUMENTS { 0, 1, 2, 3 }
--#CATEGORY  "Status Events"
--#STATE     OPERATIONAL
--#STATUS    MANDATORY
			::=  1102
		alertFanWarning TRAP-TYPE 
			ENTERPRISE storageManagementEvent
			VARIABLES { messageIDEvent, descriptionEvent, locationEvent, objectNameEvent, objectOIDEvent, 
				objectNexusEvent, currentStatusEvent, previousStatusEvent }
			DESCRIPTION 
				"Fan warning."
--#TYPE      "Storage Management Event: Fan Warning"
--#SEVERITY  MINOR
--#SUMMARY   "Alert message ID: %s, Fan warning. %s, %s, %s"
--#ARGUMENTS { 0, 1, 2, 3 }
--#CATEGORY  "Status Events"
--#STATE     DEGRADED
--#STATUS    MANDATORY
			::=  1103
		alertFanFailure TRAP-TYPE 
			ENTERPRISE storageManagementEvent
			VARIABLES { messageIDEvent, descriptionEvent, locationEvent, objectNameEvent, objectOIDEvent, 
				objectNexusEvent, currentStatusEvent, previousStatusEvent }
			DESCRIPTION 
				"Fan failure."
--#TYPE      "Storage Management Event: Fan Failure"
--#SEVERITY  CRITICAL
--#SUMMARY   "Alert message ID: %s, Fan failure. %s, %s, %s"
--#ARGUMENTS { 0, 1, 2, 3 }
--#CATEGORY  "Error Events"
--#STATE     FAILED
--#STATUS    MANDATORY
			::=  1104
		alertFanNonRecoverable TRAP-TYPE 
			ENTERPRISE storageManagementEvent
			VARIABLES { messageIDEvent, descriptionEvent, locationEvent, objectNameEvent, objectOIDEvent, 
				objectNexusEvent, currentStatusEvent, previousStatusEvent }
			DESCRIPTION 
				"Fan is non-recoverable."
--#TYPE      "Storage Management Event: Fan Non-recoverable"
--#SEVERITY  CRITICAL
--#SUMMARY   "Alert message ID: %s, Fan is non-recoverable. %s, %s, %s"
--#ARGUMENTS { 0, 1, 2, 3 }
--#CATEGORY  "Error Events"
--#STATE     FAILED
--#STATUS    MANDATORY
			::=  1105
		alertBatteryInformation TRAP-TYPE 
			ENTERPRISE storageManagementEvent
			VARIABLES { messageIDEvent, descriptionEvent, locationEvent, objectNameEvent, objectOIDEvent, 
				objectNexusEvent, currentStatusEvent, previousStatusEvent }
			DESCRIPTION 
				"Battery information."
--#TYPE      "Storage Management Event: Battery Information"
--#SEVERITY  INFORMATIONAL
--#SUMMARY   "Alert message ID: %s, Battery information. %s, %s, %s"
--#ARGUMENTS { 0, 1, 2, 3 }
--#CATEGORY  "Status Events"
--#STATE     OPERATIONAL
--#STATUS    MANDATORY
			::=  1151
		alertBatteryNormal TRAP-TYPE 
			ENTERPRISE storageManagementEvent
			VARIABLES { messageIDEvent, descriptionEvent, locationEvent, objectNameEvent, objectOIDEvent, 
				objectNexusEvent, currentStatusEvent, previousStatusEvent }
			DESCRIPTION 
				"Battery has returned to normal."
--#TYPE      "Storage Management Event: Battery Normal"
--#SEVERITY  INFORMATIONAL
--#SUMMARY   "Alert message ID: %s, Battery has returned to normal. %s, %s, %s"
--#ARGUMENTS { 0, 1, 2, 3 }
--#CATEGORY  "Status Events"
--#STATE     OPERATIONAL
--#STATUS    MANDATORY
			::=  1152
		alertBatteryWarning TRAP-TYPE 
			ENTERPRISE storageManagementEvent
			VARIABLES { messageIDEvent, descriptionEvent, locationEvent, objectNameEvent, objectOIDEvent, 
				objectNexusEvent, currentStatusEvent, previousStatusEvent }
			DESCRIPTION 
				"Battery warning."
--#TYPE      "Storage Management Event: Battery Warning"
--#SEVERITY  MINOR
--#SUMMARY   "Alert message ID: %s, Battery warning. %s, %s, %s"
--#ARGUMENTS { 0, 1, 2, 3 }
--#CATEGORY  "Status Events"
--#STATE     DEGRADED
--#STATUS    MANDATORY
			::=  1153
		alertBatteryFailure TRAP-TYPE 
			ENTERPRISE storageManagementEvent
			VARIABLES { messageIDEvent, descriptionEvent, locationEvent, objectNameEvent, objectOIDEvent, 
				objectNexusEvent, currentStatusEvent, previousStatusEvent }
			DESCRIPTION 
				"Battery failure."
--#TYPE      "Storage Management Event: Battery Failure"
--#SEVERITY  CRITICAL
--#SUMMARY   "Alert message ID: %s, Battery failure. %s, %s, %s"
--#ARGUMENTS { 0, 1, 2, 3 }
--#CATEGORY  "Error Events"
--#STATE     FAILED
--#STATUS    MANDATORY
			::=  1154
		alertBatteryNonRecoverable TRAP-TYPE 
			ENTERPRISE storageManagementEvent
			VARIABLES { messageIDEvent, descriptionEvent, locationEvent, objectNameEvent, objectOIDEvent, 
				objectNexusEvent, currentStatusEvent, previousStatusEvent }
			DESCRIPTION 
				"Battery is non-recoverable."
--#TYPE      "Storage Management Event: Battery Non-recoverable"
--#SEVERITY  CRITICAL
--#SUMMARY   "Alert message ID: %s, Battery is non-recoverable. %s, %s, %s"
--#ARGUMENTS { 0, 1, 2, 3 }
--#CATEGORY  "Error Events"
--#STATE     FAILED
--#STATUS    MANDATORY
			::=  1155
		alertVirtualDiskInformation TRAP-TYPE 
			ENTERPRISE storageManagementEvent
			VARIABLES { messageIDEvent, descriptionEvent, locationEvent, objectNameEvent, objectOIDEvent, 
				objectNexusEvent, currentStatusEvent, previousStatusEvent }
			DESCRIPTION 
				"Virtual disk information."
--#TYPE      "Storage Management Event: Virtual Disk Information"
--#SEVERITY  INFORMATIONAL
--#SUMMARY   "Alert message ID: %s, Virtual disk information. %s, %s, %s"
--#ARGUMENTS { 0, 1, 2, 3 }
--#CATEGORY  "Status Events"
--#STATE     OPERATIONAL
--#STATUS    MANDATORY
			::=  1201
		alertVirtualDiskNormal TRAP-TYPE 
			ENTERPRISE storageManagementEvent
			VARIABLES { messageIDEvent, descriptionEvent, locationEvent, objectNameEvent, objectOIDEvent, 
				objectNexusEvent, currentStatusEvent, previousStatusEvent }
			DESCRIPTION 
				"Virtual disk has returned to normal."
--#TYPE      "Storage Management Event: Virtual Disk Normal"
--#SEVERITY  INFORMATIONAL
--#SUMMARY   "Alert message ID: %s, Virtual disk has returned to normal. %s, %s, %s"
--#ARGUMENTS { 0, 1, 2, 3 }
--#CATEGORY  "Status Events"
--#STATE     OPERATIONAL
--#STATUS    MANDATORY
			::=  1202
		alertVirtualDiskWarning TRAP-TYPE 
			ENTERPRISE storageManagementEvent
			VARIABLES { messageIDEvent, descriptionEvent, locationEvent, objectNameEvent, objectOIDEvent, 
				objectNexusEvent, currentStatusEvent, previousStatusEvent }
			DESCRIPTION 
				"Virtual disk warning."
--#TYPE      "Storage Management Event: Virtual Disk Warning"
--#SEVERITY  MINOR
--#SUMMARY   "Alert message ID: %s, Virtual disk warning. %s, %s, %s"
--#ARGUMENTS { 0, 1, 2, 3 }
--#CATEGORY  "Status Events"
--#STATE     DEGRADED
--#STATUS    MANDATORY
			::=  1203
		alertVirtualDiskFailure TRAP-TYPE 
			ENTERPRISE storageManagementEvent
			VARIABLES { messageIDEvent, descriptionEvent, locationEvent, objectNameEvent, objectOIDEvent, 
				objectNexusEvent, currentStatusEvent, previousStatusEvent }
			DESCRIPTION 
				"Virtual disk failure."
--#TYPE      "Storage Management Event: Virtual Disk Failure"
--#SEVERITY  CRITICAL
--#SUMMARY   "Alert message ID: %s, Virtual disk failure. %s, %s, %s"
--#ARGUMENTS { 0, 1, 2, 3 }
--#CATEGORY  "Error Events"
--#STATE     FAILED
--#STATUS    MANDATORY
			::=  1204
		alertVirtualDiskNonRecoverable TRAP-TYPE 
			ENTERPRISE storageManagementEvent
			VARIABLES { messageIDEvent, descriptionEvent, locationEvent, objectNameEvent, objectOIDEvent, 
				objectNexusEvent, currentStatusEvent, previousStatusEvent }
			DESCRIPTION 
				"Virtual disk is non-recoverable."
--#TYPE      "Storage Management Event: Virtual Disk Non-recoverable"
--#SEVERITY  CRITICAL
--#SUMMARY   "Alert message ID: %s, Virtual disk is non-recoverable. %s, %s, %s"
--#ARGUMENTS { 0, 1, 2, 3 }
--#CATEGORY  "Error Events"
--#STATE     FAILED
--#STATUS    MANDATORY
			::=  1205
		alertRedundancyNormal TRAP-TYPE 
			ENTERPRISE storageManagementEvent
			VARIABLES { messageIDEvent, descriptionEvent, locationEvent, objectNameEvent, objectOIDEvent, 
				objectNexusEvent, currentStatusEvent, previousStatusEvent }
			DESCRIPTION 
				"Redundancy has returned to normal."
--#TYPE      "Storage Management Event: Redundancy Normal"
--#SEVERITY  INFORMATIONAL
--#SUMMARY   "Alert message ID: %s, Redundancy has returned to normal. %s, %s, %s"
--#ARGUMENTS { 0, 1, 2, 3 }
--#CATEGORY  "Status Events"
--#STATE     OPERATIONAL
--#STATUS    MANDATORY
			::=  1304
		alertRedundancyDegraded TRAP-TYPE 
			ENTERPRISE storageManagementEvent
			VARIABLES { messageIDEvent, descriptionEvent, locationEvent, objectNameEvent, objectOIDEvent, 
				objectNexusEvent, currentStatusEvent, previousStatusEvent }
			DESCRIPTION 
				"Redundancy has been degraded."
--#TYPE      "Storage Management Event: Redundancy Degraded"
--#SEVERITY  MINOR
--#SUMMARY   "Alert message ID: %s, Redundancy has been degraded. %s, %s, %s"
--#ARGUMENTS { 0, 1, 2, 3 }
--#CATEGORY  "Status Events"
--#STATE     DEGRADED
--#STATUS    MANDATORY
			::=  1305
		alertRedundancyLost TRAP-TYPE 
			ENTERPRISE storageManagementEvent
			VARIABLES { messageIDEvent, descriptionEvent, locationEvent, objectNameEvent, objectOIDEvent, 
				objectNexusEvent, currentStatusEvent, previousStatusEvent }
			DESCRIPTION 
				"Redundancy has been lost."
--#TYPE      "Storage Management Event: Redundancy Lost"
--#SEVERITY  MINOR
--#SUMMARY   "Alert message ID: %s, Redundancy has been lost. %s, %s, %s"
--#ARGUMENTS { 0, 1, 2, 3 }
--#CATEGORY  "Error Events"
--#STATE     DEGRADED
--#STATUS    MANDATORY
			::=  1306
	
	END

--
-- dcstorag.mib
--
